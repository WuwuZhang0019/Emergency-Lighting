;; Date: 2026-10-11. Explicit legacy import: backup, choose conflicts, then edit drafts.
(defun EL:DLImportAdd (row rows)
  (if (vl-some '(lambda (old) (and (equal (EL:Get 'key old) (EL:Get 'key row))
      (equal (EL:Get 'display old) (EL:Get 'display row)) (equal (EL:Get 'watts old) (EL:Get 'watts row))
      (equal (EL:Get 'zero-confirmed old) (EL:Get 'zero-confirmed row)))) rows) rows (append rows (list row))))
(defun EL:DLImportCandidates (powers devices / rows pair device name row)
  (foreach pair powers
    (setq name (car pair) row (list (cons 'key (EL:DLNameKey name)) (cons 'name name) (cons 'display name)
      (cons 'watts (cdr pair)) '(zero-confirmed) '(origin . "旧图块功率")) rows (EL:DLImportAdd row rows)))
  (foreach device devices
    (setq name (car (EL:Get 'identity device)) row (list (cons 'key (EL:DLNameKey name)) (cons 'name name)
      (cons 'display (EL:Get 'display device)) (cons 'watts (EL:Get 'watts device))
      (cons 'zero-confirmed (EL:Get 'zero-confirmed device)) '(origin . "旧设备资料")) rows (EL:DLImportAdd row rows))) rows)
(defun EL:DLImportConflict (row rows)
  (> (length (vl-remove-if-not '(lambda (other) (equal (EL:Get 'key row) (EL:Get 'key other))) rows)) 1))
(defun EL:DLLegacyRead (paths / powers devices path raw checked)
  (foreach path paths
    (EL:Require (and (findfile path) (<= (vl-file-size path) 8388608)) "旧资料文件缺失或过大，未导入。")
    (setq raw (EL:ReadData path))
    (if (equal (strcase (vl-filename-base path)) "BLOCK-POWERS")
      (progn (setq checked (vl-catch-all-apply 'EL:SimplePowersValid (list raw)))
        (EL:Require (and raw (not (vl-catch-all-error-p checked)) checked) "旧图块功率格式无效，原文件保留。")
        (setq powers (EL:Get 'powers raw)))
      (progn (EL:Require (equal (strcase (vl-filename-base path)) "DEVICE-LIBRARY") "请选择旧 config 中的 block-powers.eld 或 device-library.eld。")
        (setq checked (vl-catch-all-apply 'EL:LibraryValid (list raw)))
        (EL:Require (and raw (not (vl-catch-all-error-p checked)) checked) "旧设备资料格式无效，原文件保留。")
        (setq devices (EL:Get 'devices raw)))))
  (EL:DLImportCandidates powers devices))
(defun EL:DLLegacyBackup (snapshot paths / folder path backup)
  (setq folder (strcat (EL:Get 'root snapshot) "history/legacy/" (EL:DLOperationID)))
  (EL:Require (and (EL:DLMkdir (strcat (EL:Get 'root snapshot) "history/legacy")) (EL:DLFolderClaim folder)) "旧资料备份目录不可写，未导入。")
  (foreach path paths
    (setq backup (strcat folder "/" (vl-filename-base path) ".eld"))
    (EL:Require (and (vl-file-copy path backup) (EL:DLFilesEqual path backup)) "旧资料备份回读失败，未导入；原文件保留。")) folder)
(defun EL:DLImportDrafts (selected / catalog occupied keys row name entry entries drafts)
  (setq catalog (EL:Get 'catalog (EL:Get 'snapshot *EL:DLUIState*)) occupied (EL:Get 'devices catalog)
    drafts (EL:Get 'drafts *EL:DLUIState*))
  (foreach row drafts (setq occupied (append occupied (list (cdr row)))))
  ;; Validate every choice before touching the editor. Never overwrite an existing name.
  (foreach row selected
    (setq name (EL:Get 'key row))
    (EL:Require (and name (not (member name keys)) (EL:DLInt (EL:Get 'watts row))
      (not (vl-some '(lambda (old) (and (not (equal (EL:Get 'status old) 'deleted))
        (vl-some '(lambda (alias) (equal name (EL:DLNameKey alias))) (EL:DLEntryNames old)))) occupied)))
      "选中项同名冲突或已有同名设备；请只选择一种参数，已有项请直接编辑。")
    (setq keys (cons name keys)))
  (foreach row selected
    (setq entry (EL:DLEntryNew (EL:Put 'devices occupied catalog) (EL:Get 'name row))
      entry (EL:Put 'watts-text (itoa (EL:Get 'watts row)) (EL:Put 'watts (EL:Get 'watts row)
        (EL:Put 'display (EL:Get 'display row) (EL:Put 'zero-confirmed (EL:Get 'zero-confirmed row) entry))))
      occupied (append occupied (list entry)) entries (append entries (list entry))
      drafts (EL:Put (EL:Get 'device-id entry) entry drafts)))
  (if entries (setq *EL:DLUIState* (EL:Put 'selected (EL:Get 'device-id (car entries))
    (EL:Put 'query "" (EL:Put 'drafts drafts *EL:DLUIState*))))) (length entries))
(defun EL:DLImportAccept (/ indices index selected result)
  (setq indices (EL:StoreParse (strcat "(" (get_tile "di_rows") ")")))
  (foreach index indices (if (and (EL:DLInt index) (< index (length *EL:DLImportRows*)))
    (setq selected (append selected (list (nth index *EL:DLImportRows*))))))
  (if (not selected) (set_tile "di_status" "请选中要导入的资料；同名冲突只选一项。")
    (progn (setq result (vl-catch-all-apply 'EL:DLImportDrafts (list selected)))
      (if (vl-catch-all-error-p result) (set_tile "di_status" (cond (*EL:DLError*) (T "同名资料冲突，请重新选择。")))
        (done_dialog 1)))))
(defun EL:DLImportUIWork (/ chosen folder paths file backup dialog status row index defaults *EL:DLImportRows*)
  (setq chosen (getfiled "选择旧 config 中的 block-powers.eld 或 device-library.eld" (strcat *EL:Root* "config/block-powers.eld") "eld" 0))
  (if chosen (progn
    (EL:Require (member (strcase (vl-filename-base chosen)) '("BLOCK-POWERS" "DEVICE-LIBRARY")) "请选择旧 block-powers.eld 或 device-library.eld，未导入。")
    (setq folder (vl-filename-directory chosen))
    (foreach file '("block-powers.eld" "device-library.eld")
      (if (findfile (strcat folder "/" file)) (setq paths (append paths (list (strcat folder "/" file))))))
    (setq *EL:DLImportRows* (EL:DLLegacyRead paths))
    (EL:Require *EL:DLImportRows* "旧资料没有可导入设备，原文件保留。")
    (setq backup (EL:DLLegacyBackup (EL:Get 'snapshot *EL:DLUIState*) paths)
      dialog (load_dialog (strcat *EL:Root* "ui/device-library.dcl")))
    (setq *EL:DLLegacyConfig* (EL:NormalizeRoot folder))
    (vl-catch-all-apply 'vl-registry-write (list "HKEY_CURRENT_USER\\Software\\Emergency-Lighting\\DeviceLibrary"
      "LegacyConfig" *EL:DLLegacyConfig*))
    (if (and (> dialog 0) (new_dialog "el_device_import" dialog)) (progn
      (setq index 0 defaults "") (start_list "di_rows")
      (foreach row *EL:DLImportRows*
        (add_list (strcat (if (EL:DLImportConflict row *EL:DLImportRows*) "[同名冲突] " "")
          (EL:Get 'name row) " / " (EL:Get 'display row) " / " (itoa (EL:Get 'watts row)) "W / " (EL:Get 'origin row)))
        (if (not (EL:DLImportConflict row *EL:DLImportRows*)) (setq defaults (strcat defaults (itoa index) " ")))
        (setq index (1+ index))) (end_list) (set_tile "di_rows" defaults)
      (set_tile "di_backup" (strcat "原文件已完整备份：" backup))
      (EL:MonitorActionTile "di_accept" "(EL:DLImportAccept)") (EL:MonitorActionTile "di_cancel" "(done_dialog 0)")
      (setq status (start_dialog))))
    (if (> dialog 0) (unload_dialog dialog))
    (if (= status 1) (setq *EL:DLError* "已导入编辑草稿；请补图形和地面，核对 0W 后逐项保存。")))))
(defun EL:DLImportUI (/ result)
  (setq *EL:DLError* nil result (vl-catch-all-apply 'EL:DLImportUIWork nil))
  (if (vl-catch-all-error-p result)
    (setq *EL:DLError* (cond (*EL:DLError*) (T (vl-catch-all-error-message result))))) result)
;; Date: 2026-10-16. Transfer an independent catalog and its referenced graphics.
(defun EL:DLTransferRead (path / root raw catalog)
  (setq root (EL:NormalizeRoot (vl-filename-directory path)))
  (EL:Require (and root (not (findfile (strcat root ".write-lock")))
    (findfile path) (<= (vl-file-size path) 8388608)
    (setq raw (EL:DLReadText path) catalog (EL:DLParse raw)))
    "设备库文件无效、被占用或无法读取；请选择导出目录中的 catalog.eld。")
  (list (cons 'root root) (cons 'raw raw) (cons 'catalog catalog) '(present . T)
    (cons 'source-path path) (cons 'index (EL:DLIndex catalog))))
(defun EL:DLTransferCurrent (snapshot / path)
  (setq path (cond ((EL:Get 'source-path snapshot)) (T (strcat (EL:Get 'root snapshot) "catalog.eld"))))
  (and (not (findfile (strcat (EL:Get 'root snapshot) ".write-lock")))
    (findfile path) (equal (EL:DLReadText path) (EL:Get 'raw snapshot))))
(defun EL:DLTransferCopy (snapshot destination / root entry key relative source target loaded)
  (setq root (EL:Get 'root snapshot) destination (EL:NormalizeRoot destination))
  (EL:Require (and destination (EL:DLCatalogValid (EL:Get 'catalog snapshot))
    (EL:DLTransferCurrent snapshot)) "设备库已变化或正在保存，本次未复制，请重试。")
  (EL:Require (and (EL:DLMkdir (vl-filename-directory (vl-string-right-trim "/" destination)))
    (EL:DLFolderClaim (vl-string-right-trim "/" destination)))
    "导出或导入目录已存在或不可写；原设备库保留。")
  (foreach entry (EL:Get 'devices (EL:Get 'catalog snapshot))
    (if (> (EL:Get 'asset-revision entry) 0)
      (progn
        (EL:Require (and (EL:DLEntryAssets entry)
          (EL:DLBlockAssetValid (strcat root (EL:Get 'block-file entry))) (EL:DLLegend entry snapshot))
          (strcat "设备“" (EL:Get 'display entry) "”缺少有效图形或图例；请提供包含 assets 的完整设备库。"))
        (foreach key '(block-file legend-file)
          (setq relative (EL:Get key entry) source (strcat root relative) target (strcat destination relative))
          (EL:Require (and (EL:DLMkdir (vl-filename-directory target))
            (vl-file-copy source target) (EL:DLFilesEqual source target))
            "设备图形或图例复制核对失败；原设备库保留。")))))
  (if (findfile (setq source (strcat root "recognition-preset.eld")))
    (progn (setq target (strcat destination "recognition-preset.eld"))
      (EL:Require (and (vl-file-copy source target) (EL:DLFilesEqual source target))
        "识别预设复制核对失败；原设备库保留。")))
  ;; Publish catalog last. A failed asset copy never leaves an importable partial catalog.
  (EL:Require (EL:DLTransferCurrent snapshot) "复制期间设备库发生变化，本次未完成，请重试。")
  (EL:Require (and (EL:DLWriteText (strcat destination "catalog.eld") (EL:Get 'raw snapshot))
    (equal (EL:DLReadText (strcat destination "catalog.eld")) (EL:Get 'raw snapshot))
    (setq loaded (EL:DLSnapshotLoad destination))
    (equal (EL:Get 'catalog loaded) (EL:Get 'catalog snapshot)))
    "设备库索引写入或回读核对失败；原设备库保留。") loaded)
(defun EL:DLTransferFolderWork (shell / folder item path)
  (if (setq folder (vlax-invoke-method shell 'BrowseForFolder 0 "选择导出设备库的保存位置" 65))
    (progn (setq item (vlax-get-property folder 'Self) path (vlax-get-property item 'Path))
      (vlax-release-object item) (vlax-release-object folder) path)))
(defun EL:DLTransferFolder (/ shell result)
  (setq shell (vlax-create-object "Shell.Application")
    result (vl-catch-all-apply 'EL:DLTransferFolderWork (list shell)))
  (vlax-release-object shell)
  (if (vl-catch-all-error-p result) (EL:DLFail "无法打开目录选择窗口，请检查 Windows 文件夹访问权限。")
    (if (and result (vl-file-directory-p result)) (EL:NormalizeRoot result))))
(defun EL:DLLibraryExportWork (/ folder snapshot destination loaded opened)
  (if (setq folder (EL:DLTransferFolder))
    (progn
      (setq snapshot (EL:Get 'snapshot *EL:DLUIState*)
        destination (strcat folder "设备库-" (EL:DLOperationID) "/")
        loaded (EL:DLTransferCopy snapshot destination))
      (setq *EL:DLUINotice* (strcat "已导出设备库 "
        (itoa (length (EL:Get 'devices (EL:Get 'catalog loaded)))) " 项：" destination))
      (princ (strcat "\n" *EL:DLUINotice*))
      (setq opened (vl-catch-all-apply 'startapp (list "explorer.exe"
        (strcat "\"" (vl-string-translate "/" "\\" destination) "\"")))) destination)))
(defun EL:DLLibraryImportWork (/ path source base destination loaded old)
  (if (setq path (getfiled "导入设备库：选择完整设备库中的 catalog.eld" "" "eld" 0))
    (progn
      (setq source (EL:DLTransferRead path) base (EL:DLDefaultRoot))
      (EL:Require base "无法取得当前用户的设备库目录，未导入。")
      (setq destination (strcat base "imports/" (EL:DLOperationID) "/")
        loaded (EL:DLTransferCopy source destination) old (EL:Get 'snapshot *EL:DLUIState*))
      (EL:Require (EL:DLRootSet destination) "新库已复制，但目录设置未成功；原设备库继续使用。")
      ;; Keep the previous library and session intact; import switches to an owned copy.
      (setq *EL:DLUIDirectories* (EL:Put (EL:Get 'root old) *EL:DLUIState* *EL:DLUIDirectories*)
        *EL:DLUIState* (list (cons 'snapshot loaded) '(query . "") '(deleted) '(drafts)
          (cons 'selected (EL:Get 'device-id (car (EL:Get 'devices (EL:Get 'catalog loaded))))))
        *EL:DLCache* nil *EL:DLDefaultCache* nil
        *EL:DLUINotice* (strcat "已导入并切换设备库 "
          (itoa (length (EL:Get 'devices (EL:Get 'catalog loaded)))) " 项；原设备库保留。")) loaded)))
(defun EL:DLLibraryTransferUI (exporting / result)
  (setq *EL:DLError* nil result (vl-catch-all-apply
    (if exporting 'EL:DLLibraryExportWork 'EL:DLLibraryImportWork) nil))
  (if (vl-catch-all-error-p result)
    (progn (setq *EL:DLError* (strcat (if exporting "导出设备库未完成：" "导入设备库未完成：")
      (cond (*EL:DLError*) (T (vl-catch-all-error-message result))))) nil) result))
(princ)
