(defun EL:ClearGapPreview (/ id)
  (foreach id *EL:Highlight* (if (handent id) (redraw (handent id) 4)))
  (setq *EL:Highlight* nil) (redraw) (grtext -1 ""))
(defun EL:DrawTransient (a b color) (grdraw (trans a 0 1) (trans b 0 1) color 1))
(defun EL:MarkEnd (end label color / p tdir size x y)
  (setq p (EL:Get 'point end) size (/ (getvar "VIEWSIZE") 60.0) tdir (EL:Get 'direction end))
  (EL:DrawTransient (EL:V+ p (list (- size) 0.0 0.0)) (EL:V+ p (list size 0.0 0.0)) color)
  (EL:DrawTransient (EL:V+ p (list 0.0 (- size) 0.0)) (EL:V+ p (list 0.0 size 0.0)) color)
  ;; A/B vector glyphs; no TEXT entities are created.
  (if (= label "A")
    (progn
      (EL:DrawTransient (EL:V+ p (list size size 0.0)) (EL:V+ p (list (* 1.5 size) (* 2.0 size) 0.0)) color)
      (EL:DrawTransient (EL:V+ p (list (* 1.5 size) (* 2.0 size) 0.0)) (EL:V+ p (list (* 2.0 size) size 0.0)) color)
      (EL:DrawTransient (EL:V+ p (list (* 1.25 size) (* 1.5 size) 0.0)) (EL:V+ p (list (* 1.75 size) (* 1.5 size) 0.0)) color))
    (progn
      (EL:DrawTransient (EL:V+ p (list size size 0.0)) (EL:V+ p (list size (* 2.0 size) 0.0)) color)
      (EL:DrawTransient (EL:V+ p (list size (* 2.0 size) 0.0)) (EL:V+ p (list (* 2.0 size) (* 1.75 size) 0.0)) color)
      (EL:DrawTransient (EL:V+ p (list (* 2.0 size) (* 1.75 size) 0.0)) (EL:V+ p (list size (* 1.5 size) 0.0)) color)
      (EL:DrawTransient (EL:V+ p (list size (* 1.5 size) 0.0)) (EL:V+ p (list (* 2.0 size) (* 1.25 size) 0.0)) color)
      (EL:DrawTransient (EL:V+ p (list (* 2.0 size) (* 1.25 size) 0.0)) (EL:V+ p (list size size 0.0)) color)))
  (if tdir
    (progn
      (setq x (EL:V+ p (EL:V* (* 4.0 size) tdir)))
      (EL:DrawTransient p x color)
      (EL:DrawTransient x (EL:V+ p (EL:V* (* 3.0 size) (list (- (car tdir) (* 0.2 (cadr tdir)))
           (+ (cadr tdir) (* 0.2 (car tdir))) 0.0))) color))))
(defun EL:ShowGapPreview (a row rows snapshot / target other color candidate rec wire seg p q i)
  (EL:ClearGapPreview)
  (setq *EL:Highlight* (list (EL:Get 'wire a)) color 1)
  (if (handent (EL:Get 'wire a)) (redraw (handent (EL:Get 'wire a)) 3))
  (setq wire (EL:By 'id (EL:Get 'wire a) (EL:Get 'wires snapshot)))
  (foreach seg (EL:Get 'segments wire) (EL:DrawTransient (car seg) (cadr seg) 4))
  (if (= (length (EL:Get 'candidates row)) 1)
    (progn
      (setq target (EL:Get 'target (car (EL:Get 'candidates row))) other (EL:By 'key target rows))
      (if (and (= (length (EL:Get 'candidates other)) 1)
               (equal (EL:Get 'target (car (EL:Get 'candidates other))) (EL:Get 'key a))) (setq color 3) (setq color 2))))
  (if (> (length (EL:Get 'candidates row)) 1) (setq color 2))
  (EL:MarkEnd a "A" (if (or (EL:Get 'occupied a) (= color 1)) 1 4))
  (foreach rec (EL:Get 'candidates row)
    (setq candidate (EL:By 'key (EL:Get 'target rec) (EL:Get 'ends snapshot)))
    (if (handent (EL:Get 'wire candidate)) (redraw (handent (EL:Get 'wire candidate)) 3))
    (setq *EL:Highlight* (EL:Unique (cons (EL:Get 'wire candidate) *EL:Highlight*)))
    (foreach seg (EL:Get 'segments (EL:By 'id (EL:Get 'wire candidate) (EL:Get 'wires snapshot)))
      (EL:DrawTransient (car seg) (cadr seg) color))
    (EL:MarkEnd candidate "B" color)
    (setq p (EL:Get 'point a) q (EL:Get 'point candidate) i 0)
    (repeat 10
      (EL:DrawTransient (EL:V+ p (EL:V* (/ i 10.0) (EL:V- q p)))
        (EL:V+ p (EL:V* (/ (+ i 0.5) 10.0) (EL:V- q p))) color)
      (setq i (1+ i)))
    (if (= color 2)
      (foreach other (EL:Get 'candidates (EL:By 'key (EL:Get 'target rec) rows))
        (setq candidate (EL:By 'key (EL:Get 'target other) (EL:Get 'ends snapshot)))
        (if (handent (EL:Get 'wire candidate)) (redraw (handent (EL:Get 'wire candidate)) 3))
        (setq *EL:Highlight* (EL:Unique (cons (EL:Get 'wire candidate) *EL:Highlight*)))
        (EL:MarkEnd candidate "B" 2))))
  (cond ((EL:Get 'wire-attached a) (princ "\n这整条导线已接设备或配电箱，不参与断口搜索，请另选导线。"))
        ((EL:Get 'occupied a) (princ "\n该端已连接或存在接触疑义，不能作为自由断口。"))
        ((not (equal (EL:Get 'geometry a) 'straight)) (princ (strcat "\n端部状态：" (vl-symbol-name (EL:Get 'geometry a)))))
        ((= color 3) (princ (strcat "\n找到一对双向几何匹配；断口长度 "
          (rtos (EL:Get 'distance (car (EL:Get 'candidates row))) 2 3) " 个绘图单位。")))
        ((= color 2) (princ "\n存在多候选或反向不唯一，黄色标记包括竞争端点。"))
        (T (princ "\n搜索上限内无合格候选；详情可查看拒绝原因。")))
  (princ "\n单断口预览；整箱回路归属未核对，不保存连接。"))
(defun EL:PickEndpoint (snapshot prompt / pick id choices a b point)
  (if (setq pick (EL:PickEntity prompt))
    (progn
      (setq id (cdr (assoc 5 (entget (car pick))))
            choices (vl-remove-if-not '(lambda (x) (equal (EL:Get 'wire x) id)) (EL:Get 'ends snapshot)))
      (if (= (length choices) 2)
        (progn
          (setq point (trans (cadr pick) 1 0) a (car choices) b (cadr choices))
          (if (< (abs (- (EL:Norm (EL:V- point (EL:Get 'point a)))
                         (EL:Norm (EL:V- point (EL:Get 'point b))))) (EL:Get 'eps_touch *EL:PickParams*))
            (if (setq point (getpoint "\n两端距离相近，请明确点选端点: ")) (setq point (trans point 1 0))))
          (if point (if (< (EL:Norm (EL:V- point (EL:Get 'point a))) (EL:Norm (EL:V- point (EL:Get 'point b)))) a b)))
        (princ "\n所选对象没有两个可检查的开放端点。")))))
(defun EL:InputGapRange (params / value candidate done)
  (while (not done)
    (initget 6)
    (setq value (getreal (strcat "\n输入最大断口搜索距离（mm），应覆盖实际断口 <"
      (rtos (EL:Get 'Dmax params) 2 1) ">: ")))
    (if (not value) (setq done T)
      (progn
        (setq candidate (EL:Put 'Dmax value params))
        (if (EL:ParamsValid candidate) (setq params candidate done T)
          (princ "\n搜索距离不能小于初始搜索距离，且必须大于接触偏差，请重新输入。")))))
  params)
(defun c:ELGAPTEST (/ *error* *EL:GapStage* cfg pick layer snapshot physical rows a action params ctr size zoomed app row globalpreview)
  (defun *error* (msg)
    (EL:ClearGapPreview)
    (EL:ClearPickHighlights)
    (if zoomed (vl-catch-all-apply 'vla-ZoomCenter (list app (vlax-3d-point ctr) size)))
    (if msg (princ (strcat "\n预览已清理：" msg
      "\nELGAPTEST 失败阶段：" (cond (*EL:GapStage*) (T "初始化"))))) (princ))
  (setq *EL:GapStage* "读取设置")
  (EL:ClearPickHighlights)
  (setq cfg (EL:LoadConfig) *EL:GapStage* "读取当前视图"
        app (vlax-get-acad-object) size (getvar "VIEWSIZE")
        ctr (trans (EL:Point3 (getvar "VIEWCTR")) 2 0))
  (setq *EL:GapStage* "检查识别参数")
  (if (not cfg) (setq cfg (EL:DefaultConfig (EL:DrawingID))))
  ;; Preview needs equipment roles to enforce whole-wire exclusion.
  (if (not (EL:RolesReady cfg))
    (progn (princ "\n请先运行 ELSETUP，采样配电箱、导线和设备（可保存草稿），再检查断口。")
      (setq cfg nil)))
  (if (and cfg (not (EL:Get 'params cfg)))
    (progn
      (setq cfg (EL:Put 'params (EL:SuggestedParams) cfg))
      (princ "\n已自动采用默认识别参数，无需逐项确认。")))
  (if cfg (setq cfg (EL:UpgradeGapConfig cfg)))
  (if (and cfg (EL:Get 'wire-layers cfg) (EL:ParamsValid (EL:Get 'params cfg)))
    (progn
      (princ "\n仅检查未接设备的导线：共线、相向、同高程；非共线交叉线忽略。")
      (setq action "Next")
      (while action
        (if (member action '("Next" "Range"))
          (progn
            (EL:ClearGapPreview)
            (if (equal action "Range")
              (setq cfg (EL:Put 'params (EL:InputGapRange (EL:Get 'params cfg)) cfg)))
            (setq *EL:GapStage* "采集图形对象" snapshot (EL:CollectEndpointSnapshot cfg)
                  *EL:GapStage* "检查物理接触" physical (EL:BuildPhysical snapshot cfg nil)
                  snapshot (EL:Get 'snapshot physical) *EL:GapStage* "搜索断口候选"
                  rows (EL:FindGapCandidates snapshot cfg)
                  *EL:GapStage* "拾取断口端点"
                  *EL:PickParams* (EL:Get 'params cfg)
                  a (if (equal action "Range")
                      (EL:By 'key (EL:Get 'key a) (EL:Get 'ends snapshot))
                      (EL:PickEndpoint snapshot "\n选择打断导线的一段，靠近断口点击: ")))))
        (if a
          (progn
            (setq *EL:GapStage* "绘制断口预览" row (EL:By 'key (EL:Get 'key a) rows)) (EL:ShowGapPreview a row rows snapshot)
            (if (and *EL:Result* (EL:SourceCurrent *EL:Result* cfg snapshot))
              (progn
                (setq *EL:GapStage* "检查已有箱体上下文")
                (setq globalpreview (EL:AnalyzeSnapshot snapshot cfg (EL:Get 'panel *EL:Result*)
                  (mapcar '(lambda (c) (EL:Get 'seed c)) (EL:Get 'circuits *EL:Result*))))
                (princ (strcat "\n沿用现有箱体上下文的全局检查：" (if (EL:Get 'complete globalpreview) "识别完整" "存在未解决问题")
                  "；仍只显示预览，不提交本次结果。"))))
            (setq *EL:GapStage* "预览交互")
            (princ (strcat "\n当前搜索上限 " (rtos (EL:Get 'Dmax (EL:Get 'params cfg)) 2 1)
              " mm；断口更长时输入 R 修改上限，只需输入一个数值。"))
            (princ "\n继续检查输入 N；选错端点输入 S；范围不够输入 R；看完直接回车。")
            (princ "\n参数调整仅用于本次预览；正式统计请在 ELSETUP 中设置并核对。")
            (initget "Next Swap Range Locate Details Exit")
            (setq action (getkword "\n[Next下一处/Swap另一端/Range搜索距离/Locate放大/Details详情/Exit退出] <Exit>: "))
            (cond ((equal action "Swap")
                   (setq a (EL:By 'key (list (EL:Get 'wire a) (if (equal (EL:Get 'side a) 'start) 'end 'start)) (EL:Get 'ends snapshot))))
                  ((equal action "Details") (princ (strcat "\n" (vl-prin1-to-string row) "\n参数：" (vl-prin1-to-string (EL:Get 'params cfg)))))
                  ((equal action "Locate")
                   (setq zoomed T)
                   (vla-ZoomCenter app (vlax-3d-point (EL:Get 'point a)) (* 2.5 (EL:Get 'Dmax (EL:Get 'params cfg)))))
                  ((equal action "Exit") (setq action nil))))
          (setq action nil)))))
  (EL:ClearGapPreview)
  (EL:ClearPickHighlights)
  (if zoomed (vla-ZoomCenter app (vlax-3d-point ctr) size))
  (princ))
(defun EL:CurrentContext (cfg panel / snapshot physical seeds)
  (setq snapshot (EL:LogCall "COLLECT_SNAPSHOT" (list panel (EL:Get 'wire-layers cfg) (EL:Get 'params cfg)) 'EL:CollectEndpointSnapshot (list cfg))
        physical (EL:LogCall "BUILD_PHYSICAL" (list panel (length (EL:Get 'wires snapshot)) (length (EL:Get 'blocks snapshot))) 'EL:BuildPhysical (list snapshot cfg panel))
        snapshot (EL:Get 'snapshot physical)
        seeds (EL:LogCall "SEED_CANDIDATES" panel 'EL:SeedCandidates (list snapshot cfg panel)))
  (list snapshot seeds))
(defun EL:LocateID (id / e)
  (if (setq e (handent id)) (progn (EL:HighlightPick e) (princ (strcat "\n已高亮句柄 " id "。")))))
(defun EL:PickModel (kind prompt / pick data valid done)
  (while (not done)
    (setq pick (EL:PickEntity prompt))
    (if (not pick) (setq done T)
      (progn
        (EL:LogEvent "PICK_MODEL" (list kind (EL:LogEntity (car pick))))
        (setq data (entget (car pick))
              valid (and (equal (cdr (assoc 410 data)) "Model")
                (if (equal kind 'panel) (equal (cdr (assoc 0 data)) "INSERT")
                  (and (member (cdr (assoc 0 data)) '("LINE" "LWPOLYLINE"))
                    (= 0 (logand 1 (cond ((cdr (assoc 70 data))) (T 0))))))))
        (if valid (setq done T)
          (progn (EL:UnhighlightPick (car pick)) (princ "\n请选择模型空间内支持的对象，或回车取消。"))))))
  pick)
(defun EL:ScopeLayer (cfg layer / old)
  (foreach old (EL:Get 'wire-layers cfg)
    (if (not (equal old layer))
      (setq cfg (EL:Put 'layer-pairs (EL:Unique (cons (list old layer) (EL:Get 'layer-pairs cfg))) cfg))))
  (EL:Put 'wire-layers (EL:Unique (cons layer (EL:Get 'wire-layers cfg))) cfg))
(defun EL:PrepareBox (cfg / panel wire data record)
  (if (setq panel (EL:PickModel 'panel "\n拾取待统计配电箱: "))
    (if (setq wire (EL:PickModel 'wire "\n拾取该箱靠近出口的一段导线样本: "))
      (progn
        (setq data (entget (car panel))
              cfg (EL:ScopeLayer cfg (cdr (assoc 8 (entget (car wire)))))
              cfg (EL:Put 'params (EL:GapParams (EL:Get 'params cfg)) cfg)
              cfg (EL:Put 'units "mm" cfg))
        (EL:LogEvent "PICKS" (list (cons 'panel (EL:LogEntity (car panel))) (cons 'wire (EL:LogEntity (car wire))) (cons 'params (EL:Get 'params cfg))))
        (setq record (EL:LogCall "PANEL_RECORD" (EL:LogEntity (car panel)) 'EL:BlockRecord (list (car panel) cfg))
              cfg (EL:PutRole cfg (EL:Get 'identity record) 'panel))
        (list cfg (cdr (assoc 5 data)) (cdr (assoc 5 (entget (car wire)))))))))
(defun EL:RememberExitUI ()
  (setq *EL:ExitSelection* (get_tile "exits") *EL:ExitScope* (get_tile "scope_exclude")
        *EL:ExitRoles* (get_tile "role_recheck")))
(defun EL:RequestExitPreview (value)
  ;; Date: 2026-10-08. Only close DCL here; graphics run after START_DIALOG returns.
  (EL:RememberExitUI)
  (if (/= value "") (done_dialog 3)))
(defun EL:ReviewExits (seeds / dialog status row chosen *EL:ExitSelection* *EL:ExitScope* *EL:ExitRoles*)
  (setq dialog (load_dialog (strcat *EL:Root* "ui/power.dcl")) *EL:DialogID* dialog status 3
        *EL:ExitRows* seeds *EL:ExitRoles* "0")
  (while (and (> dialog 0) (= status 3))
    (if (new_dialog "el_exits" dialog)
      (progn
        (set_tile "scope_info" (strcat "未纳入的箱边导线：" (vl-prin1-to-string *EL:OutsidePorts*)))
        (start_list "exits")
        (foreach row seeds (add_list (strcat (EL:Get 'id row) " / 导线 " (EL:Get 'wire row) " / 点选查看图面")))
        (end_list)
        (if (not *EL:ExitSelection*)
          (progn (EL:RestoreExitSelection) (setq *EL:ExitSelection* (get_tile "exits")
            *EL:ExitScope* (get_tile "scope_exclude"))))
        (set_tile "exits" *EL:ExitSelection*) (set_tile "scope_exclude" *EL:ExitScope*)
        (set_tile "role_recheck" *EL:ExitRoles*)
        (EL:MonitorActionTile "exits" "(EL:RequestExitPreview $value)")
        (EL:MonitorActionTile "exit_preview" "(EL:RequestExitPreview (get_tile \"exits\"))")
        (EL:MonitorActionTile "exit_all" "(EL:SelectAllExits)")
        (EL:MonitorActionTile "accept" "(EL:RememberExitUI) (setq chosen *EL:ExitSelection* *EL:ScopeConfirmed* (equal *EL:ExitScope* \"1\") *EL:ReviewAllRoles* (equal *EL:ExitRoles* \"1\")) (done_dialog 1)")
        (EL:MonitorActionTile "cancel" "(done_dialog 0)")
        (EL:MonitorActionTile "add_wire" "(done_dialog 2)")
        (setq status (start_dialog))
        (if (= status 3)
          (progn
            (EL:ExitHighlight *EL:ExitSelection*)
            (getstring "\n黄色标记为选中出线；按 Enter 返回出口列表：")
            (EL:ClearGapPreview) (EL:ClearPickHighlights))))
      (setq status 0)))
  (if (> dialog 0) (unload_dialog dialog)) (setq *EL:DialogID* nil)
  (EL:ClearPickHighlights)
  (cond ((equal status 2) 'add)
        ((equal status 1) (list (mapcar '(lambda (i) (nth i seeds)) (read (strcat "(" chosen ")")))))))
(defun c:ELTRACE (/ *error* cfg panel pick context seeds selected result current task sample review done circuit fresh prior reusable *EL:ExitSnapshot*)
  (defun *error* (msg)
    (EL:LogFailure msg)
    (if panel (vl-catch-all-apply 'EL:MarkStale (list panel 'recognition-cancelled)))
    (vl-catch-all-apply 'EL:ClearGapPreview nil) (vl-catch-all-apply 'EL:ClearPickHighlights nil)
    (vl-catch-all-apply 'EL:ReleasePowerUI nil) (setq *EL:Result* nil *EL:RoleEdits* nil *EL:RoleLibraryEdits* nil)
    (if msg (princ (strcat "\n识别取消：" msg))) (princ))
  (EL:LogStart)
  (EL:ClearPickHighlights) (setq *EL:DeviceResult* nil *EL:Result* nil *EL:RoleLibraryEdits* nil *EL:ReviewAllRoles* nil)
  (if (and (setq cfg (EL:LogCall "LOAD_CONFIG" nil 'EL:LoadConfig nil))
      (progn (EL:LogAttach)
        (EL:LogEvent "CONFIG" (list (cons 'drawing (EL:Get 'drawing cfg)) (cons 'version (EL:Get 'version cfg))
          (cons 'params (EL:Get 'params cfg)) (cons 'wire-layers (EL:Get 'wire-layers cfg))))
        (setq task (EL:LogCall "PREPARE_BOX" nil 'EL:PrepareBox (list cfg)))))
    (progn
      (setq cfg (car task) panel (cadr task) *EL:ReviewPanel* panel sample (caddr task))
      (while (not done)
        (setq context (EL:CurrentContext cfg panel) seeds (cadr context)
              *EL:OutsidePorts* (EL:OutsidePorts (car context) cfg panel) *EL:ScopeConfirmed* nil
              *EL:ExitDefaults* (EL:ReusableExits cfg panel (car context)))
        (princ (strcat "\n本次导线图层：" (vl-prin1-to-string (EL:Get 'wire-layers cfg))))
        (cond
          ((EL:Get 'issues (EL:By 'id panel (EL:Get 'blocks (car context))))
            (princ "\n箱体轮廓存在未支持项，不能确认出线。") (setq done T))
          (T
            (EL:LogEvent "EXIT_CONTEXT" (list (cons 'panel panel) (cons 'sample sample)
              (cons 'panel-bounds (EL:Get 'bounds (EL:By 'id panel (EL:Get 'blocks (car context)))))
              (cons 'sample-segments (EL:Get 'segments (EL:By 'id sample (EL:Get 'wires (car context)))))
              (cons 'sample-is-exit (if (EL:By 'wire sample seeds) T nil)) (cons 'seeds seeds)))
            (if seeds
              (princ (strcat "\n已找到 " (itoa (length seeds)) " 条箱口候选；样本仅用于确定导线图层，请在列表核对实际出线。"))
              (princ "\n当前图层未发现接触箱体整体范围的导线。可在列表中补充图层，或取消后核对箱体与导线位置。"))
            (setq *EL:ExitSnapshot* (car context))
            (setq review (EL:LogCall "REVIEW_EXITS" seeds 'EL:ReviewExits (list seeds)))
            (if (equal review 'add)
              (if (setq pick (EL:PickModel 'wire "\n补充一个导线图层样本: "))
                (setq cfg (EL:ScopeLayer cfg (cdr (assoc 8 (entget (car pick))))))
                (setq done T))
              (progn (setq done T) (if review (setq selected (car review))))))))
      (setq prior (car context))
      (if selected (setq cfg (EL:LogCall "REVIEW_ROLES" panel 'EL:ReviewRoles (list prior cfg))))
      (if (and selected cfg) (setq fresh (EL:CollectEndpointSnapshot cfg)))
      (if (and selected cfg (not (equal (EL:Get 'signature prior) (EL:Get 'signature fresh))))
        (progn (princ "\nSOURCE_CHANGED：核对期间源图变化，本次选择未保存。") (setq cfg nil)))
      (if (and selected cfg) (setq cfg (EL:RememberExits cfg panel fresh selected *EL:ScopeConfirmed*)))
      (if (and selected cfg (setq cfg (EL:SaveConfig cfg)))
        (progn
          (if *EL:RoleLibraryEdits* (EL:SaveRoleLibrary *EL:RoleLibraryEdits*))
          (setq context (EL:CurrentContext cfg panel)
                result (EL:LogCall "ANALYZE_SNAPSHOT" (list panel selected) 'EL:AnalyzeSnapshot (list (car context) cfg panel selected))
                current (EL:CollectEndpointSnapshot cfg))
          (if (equal (EL:Get 'signature current) (EL:Get 'signature (car context)))
            (progn
              (if (and *EL:OutsidePorts* (not *EL:ScopeConfirmed*))
                (setq result (EL:Put 'complete nil (EL:Put 'issues
                  (cons (EL:Issue 'WIRE_SCOPE_UNCONFIRMED panel *EL:OutsidePorts*) (EL:Get 'issues result)) result))))
              (setq *EL:Result* result)
              (EL:PublishDiagram result cfg)
              (princ (strcat "\n阶段耗时与数量：" (vl-prin1-to-string (EL:Get 'timing result))))
              (foreach circuit (EL:Get 'circuits result)
                (princ (strcat "\n" (EL:Get 'id circuit) "：设备 " (itoa (length (EL:Get 'devices circuit)))
                  "，识别" (if (EL:Get 'complete circuit) "完整" "有未解决问题")))))
            (princ "\nSOURCE_CHANGED：源图已变化，请重新识别。"))))))
  (EL:ClearPickHighlights)
  (if (not *EL:Result*)
    (progn (if panel (EL:MarkStale panel 'recognition-failed)) (EL:LogEvent "NO_RESULT_REASON" (if selected 'review-or-source-not-confirmed 'no-exits-confirmed))
      (princ "\n本次未生成统计结果：出线未确认、核对已取消或源图校验未通过。")))
  (EL:LogFinish (if *EL:Result* 'result-ready 'no-result)) (princ))
(defun EL:ResolveGapManually (cfg / context snapshot seeds physical a b metrics exception pair result checked panel pick)
  (if (setq pick (EL:PickEntity "\n拾取该断口所属箱体（用于全局核对）: "))
    (if (and (= (cdr (assoc 0 (entget (car pick)))) "INSERT") (= (cdr (assoc 410 (entget (car pick)))) "Model")
             (equal (EL:Get 'role (EL:BlockRecord (car pick) cfg)) 'panel))
      (progn
      (setq panel (cdr (assoc 5 (entget (car pick)))) context (EL:CurrentContext cfg panel)
            snapshot (car context) seeds (cadr context) *EL:PickParams* (EL:Get 'params cfg)
            a (EL:PickEndpoint snapshot "\n点选第一个具体断口端点: "))
      (if a (setq b (EL:PickEndpoint snapshot "\n点选另一具体断口端点: ")))
      (if (and seeds a b (not (EL:Get 'occupied a)) (not (EL:Get 'occupied b)))
        (progn
          (setq metrics (EL:ValidateGapPair a b snapshot cfg))
          (princ (strcat "\n几何判据：" (vl-prin1-to-string metrics)))
          (setq exception (getstring T "\n人工确认原因（不能为空；超距或非共线需说明）: "))
          (initget "Yes No")
          (if (and (/= exception "") (equal (getkword "\n确认这两个具体端点的原接线？[Yes/No] <No>: ") "Yes"))
            (progn
              (setq pair (list (cons 'a (EL:Get 'key a)) (cons 'b (EL:Get 'key b)) (cons 'source 'manual)
                (cons 'signature (EL:Get 'signature snapshot)) (cons 'params (EL:Get 'params cfg)) (cons 'rules (EL:Get 'roles cfg))
                (cons 'drawing (EL:Get 'drawing cfg)) (cons 'date (getvar "CDATE")) (cons 'exception exception)
                (cons 'a-state (EL:Signature a)) (cons 'b-state (EL:Signature b))))
              (setq cfg (EL:Put 'gap-pairs (cons pair (EL:Get 'gap-pairs cfg)) cfg)
                    result (EL:AnalyzeSnapshot snapshot cfg panel seeds))
              (if (and (member pair (EL:Get 'connections result))
                       (equal (EL:Get 'signature snapshot) (EL:Get 'signature (EL:CollectEndpointSnapshot cfg))))
                (EL:SaveConfig cfg) (princ "\n端点占用、回路归属或源图校验未通过；配对未保存。")))))))
      (princ "\n请选择已配置的模型空间配电箱。"))))
(defun c:ELPAIRGAP (/ *error* cfg)
  (defun *error* (msg)
    (EL:ClearPickHighlights)
    (if msg (princ (strcat "\n断口配对取消，拾取亮显已清理：" msg))) (princ))
  (EL:ClearPickHighlights)
  (if (and (setq cfg (EL:LoadConfig)) (EL:ParamsValid (EL:Get 'params cfg))) (EL:ResolveGapManually cfg))
  (EL:ClearPickHighlights) (princ))
(defun c:ELPAIRLEADER (/ *error* cfg a b ea eb snapshot ra rb pair context result)
  (defun *error* (msg)
    (EL:ClearPickHighlights)
    (if msg (princ (strcat "\n引线配对取消，拾取亮显已清理：" msg))) (princ))
  (EL:ClearPickHighlights)
  (if (and (setq cfg (EL:LoadConfig)) (EL:ParamsValid (EL:Get 'params cfg)))
    (progn
      (setq a (EL:PickEntity "\n拾取第一个引线图块: "))
      (if a (setq b (EL:PickEntity "\n拾取配对楼层的引线图块: ")))
      (if (and a b (not (equal (car a) (car b)))
               (= (cdr (assoc 0 (entget (car a)))) "INSERT") (= (cdr (assoc 0 (entget (car b)))) "INSERT"))
        (progn
          (foreach ea (list (car a) (car b))
            (setq cfg (EL:Put 'leader-layers (EL:Unique (cons (cdr (assoc 8 (entget ea))) (EL:Get 'leader-layers cfg))) cfg)
                  cfg (EL:Put 'leader-names (EL:Unique (cons (EL:EffectiveName ea) (EL:Get 'leader-names cfg))) cfg)))
          (setq snapshot (EL:CollectEndpointSnapshot cfg)
                ra (EL:By 'id (cdr (assoc 5 (entget (car a)))) (EL:Get 'blocks snapshot))
                rb (EL:By 'id (cdr (assoc 5 (entget (car b)))) (EL:Get 'blocks snapshot)))
          (if (vl-some '(lambda (p) (or (member (EL:Get 'a p) (list (EL:Get 'id ra) (EL:Get 'id rb)))
                      (member (EL:Get 'b p) (list (EL:Get 'id ra) (EL:Get 'id rb))))) (EL:Get 'leader-pairs cfg))
            (princ "\n至少一个引线已有配对；先用 ELCLEARPAIRS 清理失效关系。")
            (progn
              (setq pair (list (cons 'a (EL:Get 'id ra)) (cons 'b (EL:Get 'id rb))
                    (cons 'a-state (EL:Get 'raw ra)) (cons 'b-state (EL:Get 'raw rb))
                    (cons 'drawing (EL:Get 'drawing cfg)) (cons 'date (getvar "CDATE"))))
              (initget "Yes No")
              (if (equal (getkword "\n确认该对引线？[Yes/No] <No>: ") "Yes")
                (EL:SaveConfig (EL:Put 'leader-pairs (cons pair (EL:Get 'leader-pairs cfg)) cfg)))))))))
  (EL:ClearPickHighlights) (princ))
(defun c:ELCLEARPAIRS (/ cfg kind)
  (if (setq cfg (EL:LoadConfig))
    (progn
      (initget "Gap Leader") (setq kind (getkword "\n清理本图配对类型 [Gap/Leader]: "))
      (if kind (EL:SaveConfig (EL:Put (if (= kind "Gap") 'gap-pairs 'leader-pairs) nil cfg))))) (princ))
(defun EL:PowerUISelect (index / row record category)
  (setq *EL:PowerIndex* index row (nth index *EL:PowerRows*)
        record (EL:ResolvePower (EL:Get 'identity row) *EL:PowerEdits* (EL:Get 'powers *EL:PowerCfg*) *EL:PowerLibrary*)
        category (EL:Get 'category record))
  (set_tile "category" (cond ((equal category 'lighting) "1") ((equal category 'sign) "2") ((equal category 'exit) "3") ((equal category 'other) "4") (T "0")))
  (set_tile "display" (cond ((EL:Get 'display record)) ((EL:Get 'name row)) (T "")))
  (set_tile "watts" (if (EL:Get 'watts record) (itoa (EL:Get 'watts record)) ""))
  (set_tile "zero" (if (EL:Get 'zero-confirmed record) "1" "0"))
  (set_tile "source" (strcat "动态状态：" (vl-prin1-to-string (cadr (EL:Get 'identity row)))
    "  值来源：" (cond ((not record) "未配置；请确认类别") ((equal (EL:Get 'source record) 'current-input) "本次输入")
      ((equal (EL:Get 'source record) 'drawing-saved) "本图保存") (T "项目设备库"))))
  (if (and (not record) (vl-some '(lambda (r) (equal (car (EL:Get 'identity r)) (EL:Get 'name row)))
           (append (EL:Get 'powers *EL:PowerCfg*) *EL:PowerLibrary*)))
    (set_tile "source" "存在同名但定义／动态状态不同的配置，须重新核对类别及功率。"))
  (set_tile "error" ""))
(defun EL:PowerUICategory (value / category watts)
  (setq category (nth (atoi value) '(nil lighting sign exit other)) watts (EL:DefaultWatts category))
  (if (and watts (= (get_tile "watts") "")) (set_tile "watts" (itoa watts))))
(defun EL:PowerUISave (/ row record old w)
  (setq row (nth *EL:PowerIndex* *EL:PowerRows*) w (EL:ParseWatts (get_tile "watts"))
        record (list (cons 'identity (EL:Get 'identity row))
          (cons 'category (nth (atoi (get_tile "category")) '(nil lighting sign exit other)))
          (cons 'display (get_tile "display")) (cons 'watts w)
          (cons 'zero-confirmed (= (get_tile "zero") "1")) (cons 'source 'current-input)))
  (if (EL:PowerValid record)
    (progn
      (setq old (EL:By 'identity (EL:Get 'identity row) *EL:PowerEdits*))
      (setq *EL:PowerEdits* (if old (subst record old *EL:PowerEdits*) (cons record *EL:PowerEdits*)))
      (set_tile "error" "本行已保存到本次编辑；点击应用后持久化。") T)
    (progn (set_tile "error" "请选择类别、填写名称和非负整数功率；0W 必须勾选用途确认。") nil)))
(defun EL:ReleasePowerUI ()
  (EL:ThumbCleanup)
  (if (and *EL:DialogID* (> *EL:DialogID* 0)) (unload_dialog *EL:DialogID*))
  (setq *EL:DialogID* nil *EL:PowerRows* nil *EL:PowerEdits* nil *EL:PowerIndex* nil
        *EL:PowerCfg* nil *EL:PowerLibrary* nil *EL:PowerResult* nil *EL:CircuitIndex* nil))
(defun EL:PowerUIRefresh (/ view circuit row record label)
  (setq *EL:PowerResult* (EL:BoxStatistics *EL:PowerResult* *EL:PowerCfg* *EL:PowerLibrary* *EL:PowerEdits*)
        view *EL:PowerResult*)
  (if (> *EL:CircuitIndex* 0)
    (setq view (EL:Put 'circuits (list (nth (1- *EL:CircuitIndex*) (EL:Get 'circuits view))) view)))
  (setq *EL:PowerRows* (EL:PowerTableRows view) *EL:PowerIndex* 0)
  (start_list "circuit_rows")
  (add_list (strcat "全部回路 / 完整回路合计 " (itoa (EL:Get 'box-watts *EL:PowerResult*)) "W / "
    (if (EL:Get 'complete *EL:PowerResult*) "识别完整" "整箱未完成")))
  (foreach circuit (EL:Get 'circuits *EL:PowerResult*)
    (add_list (strcat (EL:Get 'id circuit) " / 出口 " (vl-prin1-to-string (EL:Get 'point (EL:Get 'seed circuit)))
      " / 设备 " (itoa (length (EL:Get 'devices circuit))) " / " (itoa (EL:Get 'watts circuit)) "W / "
      (if (EL:Get 'complete circuit) "完整" "未完成或冲突")
      (if (EL:Get 'over-limit circuit) " / 超过172W" "")
      (if (EL:Get 'power-values-complete circuit) "" " / 功率缺项"))))
  (end_list) (set_tile "circuit_rows" (itoa *EL:CircuitIndex*))
  (start_list "rows")
  (foreach row *EL:PowerRows*
    (setq record (EL:ResolvePower (EL:Get 'identity row) *EL:PowerEdits* (EL:Get 'powers *EL:PowerCfg*) *EL:PowerLibrary*))
    (add_list (strcat (EL:Get 'name row) " / 身份 " (EL:Hash (EL:Signature (EL:Get 'identity row)))
      " / 数量 " (itoa (EL:Get 'count row)) " / " (vl-prin1-to-string (EL:Get 'circuits row))
      " / " (if (EL:PowerValid record)
        (strcat (itoa (EL:Get 'watts record)) "W / 小计 " (rtos (* 1.0 (EL:Get 'count row) (EL:Get 'watts record)) 2 0) "W") "功率待填"))))
  (end_list) (set_tile "rows" "0")
  (if *EL:PowerRows* (EL:PowerUISelect 0)))
(defun EL:PowerCircuitSelect (value / circuit id)
  (setq *EL:CircuitIndex* (atoi value))
  (EL:ClearPickHighlights)
  (if (> *EL:CircuitIndex* 0)
    (progn
      (setq circuit (nth (1- *EL:CircuitIndex*) (EL:Get 'circuits *EL:PowerResult*)))
      (foreach id (EL:Get 'objects circuit) (EL:LocateID id))))
  (EL:PowerUIRefresh))
(defun EL:PowerHighlight (index / id)
  (EL:ClearPickHighlights) (EL:PowerUISelect index)
  (foreach id (EL:Get 'ids (nth index *EL:PowerRows*)) (EL:LocateID id)))
(defun EL:PowerDialog (result cfg library / dialog status row id)
  (setq *EL:PowerResult* result *EL:CircuitIndex* 0 *EL:PowerEdits* nil *EL:PowerIndex* 0
        *EL:SaveLibrary* nil *EL:LibraryEdits* nil
        *EL:PowerCfg* cfg *EL:PowerLibrary* library dialog (load_dialog (strcat *EL:Root* "ui/power.dcl")) *EL:DialogID* dialog)
  (if (> dialog 0)
    (progn
      (setq status 2)
      (while (= status 2)
        (if (new_dialog "el_power" dialog)
          (progn
            (start_list "category") (foreach row '("请选择类别" "应急照明灯（默认5W）" "疏散标志（默认1W）" "安全出口（默认1W）" "其他（手填）") (add_list row)) (end_list)
            (EL:PowerUIRefresh)
            (EL:MonitorActionTile "rows" "(EL:PowerHighlight (atoi $value))")
            (EL:MonitorActionTile "circuit_rows" "(EL:PowerCircuitSelect $value)")
            (EL:MonitorActionTile "category" "(EL:PowerUICategory $value)")
            (EL:MonitorActionTile "save_row" "(if (EL:PowerUISave) (EL:PowerUIRefresh))")
            (EL:MonitorActionTile "locate" "(done_dialog 2)")
            (EL:MonitorActionTile "accept" "(setq *EL:SaveLibrary* (equal (get_tile \"save_library\") \"1\")) (done_dialog 1)")
            (EL:MonitorActionTile "cancel" "(done_dialog 0)")
            (setq status (start_dialog))
            (if (= status 2)
              (progn
                (EL:PowerHighlight *EL:PowerIndex*)
                (getstring "\n按 Enter 返回功率表: ") (EL:ClearPickHighlights))))
          (setq status 0)))
      (unload_dialog dialog) (setq *EL:DialogID* nil)
      (if (= status 1)
        (progn (setq *EL:LibraryEdits* *EL:PowerEdits*)
          (EL:Put 'powers (EL:MergePowers (EL:Get 'powers cfg) *EL:PowerEdits*) cfg))))
    (princ "\n无法打开 DCL 功率表。")))
(defun c:ELPOWER ()
  (if (equal (EL:Get 'engine *EL:Result*) 'fixed) (EL:EditPanel *EL:Result* *EL:FixedConfig*)
    (if *EL:DeviceResult* (EL:SimpleEdit *EL:DeviceResult*) (EL:AdvancedPower))) (princ))
(defun EL:AdvancedPower (/ *error* cfg library edited)
  (defun *error* (msg) (EL:ClearGapPreview) (EL:ClearPickHighlights) (EL:ReleasePowerUI) (if msg (princ (strcat "\n功率编辑取消，未应用的行未保存：" msg))) (princ))
  (EL:ClearPickHighlights)
  (if (and *EL:Result* (setq cfg (EL:LoadConfig))
           (EL:SourceCurrent *EL:Result* cfg (EL:CollectEndpointSnapshot cfg)))
    (progn
      (setq library (EL:LoadLibrary) *EL:Result* (EL:BoxStatistics *EL:Result* cfg library nil)
            edited (EL:PowerDialog *EL:Result* cfg library))
      (EL:ReleasePowerUI)
      (if edited
        (if (and (EL:SourceCurrent *EL:Result* edited (EL:CollectEndpointSnapshot edited)) (setq cfg (EL:SaveConfig edited)))
          (progn
            (if *EL:SaveLibrary* (EL:SavePowerLibrary *EL:LibraryEdits*))
            (setq *EL:Result* (EL:BoxStatistics *EL:Result* cfg library nil)) (EL:PrintStatistics *EL:Result*) (EL:PublishDiagram *EL:Result* cfg)))))
    (princ "\n本图没有有效统计或源图／识别配置已变化，请运行 ELTRACE。")) (EL:ClearPickHighlights) (princ))
(defun c:ELISSUES (/ rows index i issue object)
  (if *EL:Result*
    (progn
      (setq rows (append (EL:Get 'issues *EL:Result*) (EL:Get 'unrelated-issues *EL:Result*)) i 0)
      (foreach issue (EL:Get 'circuits *EL:Result*)
        (setq rows (append rows (EL:Get 'issues issue) (EL:Get 'power-issues issue))))
      (setq rows (EL:Unique rows))
      (foreach issue rows
        (setq i (1+ i)) (princ (strcat "\n" (itoa i) "：" (vl-prin1-to-string issue))))
      (if rows
        (progn
          (setq index (getint "\n输入问题序号定位（Enter 退出）: "))
          (if (and index (> index 0) (<= index (length rows)))
            (progn
              (setq object (EL:Get 'object (nth (1- index) rows)))
              (if (equal (type object) 'STR) (EL:LocateID object)
                (foreach i object (if (equal (type i) 'STR) (EL:LocateID i)))))))))) (princ))
;; Date: 2026-10-12. Resume an owned preview job before opening another statistics window.
(defun c:ELSTAT ()
  ;; Date: 2026-10-15. A pending legend must not lock the parameter editor.
  (if *EL:DLCaptureJob* (setq *EL:DLParentContinue* nil))
  (EL:FixedStat) (princ))
(defun c:ELSAVERESULT (/ path cfg)
  (if (and *EL:Result* (setq cfg (EL:LoadConfig))
       (EL:SourceCurrent *EL:Result* cfg (EL:CollectEndpointSnapshot cfg)))
    (progn
      (setq *EL:Result* (EL:BoxStatistics *EL:Result* cfg (EL:LoadLibrary) nil)
            path (strcat *EL:Root* "output/statistics-" (EL:Hash (EL:Get 'drawing *EL:Result*)) ".eld"))
      (if (EL:WriteData path (list (cons 'version 2) (cons 'date (getvar "CDATE")) (cons 'result *EL:Result*)))
        (princ (strcat "\n结果已保存：" path))))
    (princ "\n结果不存在或依据已变化，请重新识别。")) (princ))
(defun EL:UnknownRows (snapshot cfg / rows block wire row)
  (foreach block (EL:Get 'blocks snapshot)
    (if (and (not (equal (EL:Get 'id block) *EL:ReviewPanel*))
          (or *EL:ReviewAllRoles* (member (EL:Get 'role block) '(unknown ambiguous)))
          (vl-some '(lambda (w) (EL:PathBlockHit w block cfg)) (EL:Get 'wires snapshot)))
      (progn
        (setq row (EL:By 'identity (EL:Get 'identity block) rows))
        (if row (setq rows (subst (EL:Put 'ids (cons (EL:Get 'id block) (EL:Get 'ids row)) row) row rows))
          (setq rows (cons (list (cons 'identity (EL:Get 'identity block)) (cons 'role (EL:Get 'role block)) (cons 'name (EL:Get 'name block))
            (cons 'ids (list (EL:Get 'id block)))) rows))))))
  (reverse rows))
(defun EL:RoleUIApply (/ row old record)
  (setq row (nth (atoi (get_tile "role_rows")) *EL:RoleRows*)
        record (list (cons 'identity (EL:Get 'identity row))
          (cons 'role (nth (atoi (get_tile "role_choice")) '(unknown device panel leader ignore))) (cons 'confirmed T)))
  (if (EL:RoleShape record)
    (progn
      (setq old (EL:By 'identity (EL:Get 'identity row) *EL:RoleEdits*)
            *EL:RoleEdits* (if old (subst record old *EL:RoleEdits*) (cons record *EL:RoleEdits*)))
      (set_tile "role_status" (strcat "已确认 " (itoa (length *EL:RoleEdits*)) " 类，点击应用后使用。")))))
(defun EL:ReviewRoles (snapshot cfg / dialog status row id)
  (setq *EL:RoleRows* (EL:UnknownRows snapshot cfg) *EL:RoleEdits* nil)
  (if *EL:RoleRows*
    (progn
      (setq dialog (load_dialog (strcat *EL:Root* "ui/power.dcl")) *EL:DialogID* dialog status 2)
      (while (and (> dialog 0) (= status 2))
        (if (new_dialog "el_roles" dialog)
          (progn
            (start_list "role_rows")
            (foreach row *EL:RoleRows* (add_list (strcat (EL:Get 'name row) " / " (itoa (length (EL:Get 'ids row)))
              " / 当前 " (vl-prin1-to-string (EL:Get 'role row)) " / 身份 " (EL:Hash (EL:Signature (EL:Get 'identity row)))))) (end_list)
            (start_list "role_choice") (foreach row '("待核对" "设备" "配电箱" "跨层引线" "忽略") (add_list row)) (end_list)
            (set_tile "role_rows" "0") (set_tile "role_choice" "0")
            (EL:MonitorActionTile "role_apply" "(EL:RoleUIApply)")
            (EL:MonitorActionTile "role_locate" "(setq row (nth (atoi (get_tile \"role_rows\")) *EL:RoleRows*)) (done_dialog 2)")
            (EL:MonitorActionTile "accept" "(if (equal (get_tile \"role_library\") \"1\") (setq *EL:RoleLibraryEdits* *EL:RoleEdits*)) (done_dialog 1)") (EL:MonitorActionTile "cancel" "(done_dialog 0)")
            (setq status (start_dialog))
            (if (= status 2)
              (progn (EL:ClearPickHighlights) (foreach id (EL:Get 'ids row) (EL:LocateID id))
                (getstring "\n按 Enter 返回分类表: ") (EL:ClearPickHighlights))))
          (setq status 0)))
      (if (> dialog 0) (unload_dialog dialog)) (setq *EL:DialogID* nil)
      (if (= status 1)
        (foreach row *EL:RoleEdits* (setq cfg (EL:PutRole cfg (EL:Get 'identity row) (EL:Get 'role row))))
        (setq cfg nil))))
  (setq *EL:RoleRows* nil *EL:RoleEdits* nil)
  cfg)

(defun EL:OutsidePorts (snapshot cfg panel / block ports wire ep)
  (setq block (EL:By 'id panel (EL:Get 'blocks snapshot)))
  (foreach wire (EL:Get 'outside-wires snapshot)
    (foreach ep (EL:Get 'ends wire)
      (if (EL:BlockPointHit (EL:Get 'point ep) block cfg)
        (setq ports (cons (list (EL:Get 'id wire) (EL:Get 'layer wire)) ports)))))
  (EL:Unique ports))
(defun EL:ExitHighlight (value / index row wire seg p size)
  (EL:ClearGapPreview) (EL:ClearPickHighlights)
  (setq size (/ (getvar "VIEWSIZE") 60.0))
  (foreach index (read (strcat "(" value ")"))
    (setq row (nth index *EL:ExitRows*) wire (EL:By 'id (EL:Get 'wire row) (EL:Get 'wires *EL:ExitSnapshot*)))
    (EL:LocateID (EL:Get 'wire row))
    (foreach seg (EL:Get 'segments wire) (EL:DrawTransient (car seg) (cadr seg) 2))
    (setq p (EL:Get 'point row))
    (if p
      (foreach seg (EL:BoundsSegments (list (EL:V- p (list size size 0.0)) (EL:V+ p (list size size 0.0))))
        (EL:DrawTransient (car seg) (cadr seg) 2)))
    (princ (strcat "\n正在查看 " (EL:Get 'id row) " / 导线 " (EL:Get 'wire row)))))
(defun EL:SelectAllExits (/ value index)
  (setq value "" index 0)
  (repeat (length *EL:ExitRows*) (setq value (strcat value (itoa index) " ") index (1+ index)))
  (set_tile "exits" value) (EL:RememberExitUI))

(defun EL:RestoreExitSelection (/ index value seed)
  (setq index 0 value "")
  (foreach seed *EL:ExitRows*
    (if (member (EL:Get 'key seed) (EL:Get 'keys *EL:ExitDefaults*)) (setq value (strcat value (itoa index) " ")))
    (setq index (1+ index)))
  (set_tile "exits" value)
  (set_tile "scope_exclude" (if (EL:Get 'scope-excluded *EL:ExitDefaults*) "1" "0")))

(defun c:ELSAVELIB (/ cfg)
  (if (setq cfg (EL:LoadConfig))
    (if (and (EL:SavePowerLibrary (EL:Get 'powers cfg)) (EL:SaveRoleLibrary (EL:Get 'roles cfg)))
      (princ "\n本图已确认的角色与功率已保存到设备库。"))) (princ))
