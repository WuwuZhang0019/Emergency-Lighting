;; Date: 2026-10-08. Status: frozen v16 host-only contact oracle.
(defun TEST16:Touches (p segments tol epsz / hit seg)
  (foreach seg segments
    (if (and (<= (EL:PointSegmentDistance p (car seg) (cadr seg)) tol)
             (<= (abs (- (caddr p) (caddr (car seg)))) epsz)) (setq hit T))) hit)
(defun TEST16:RegionContains (point block / hit loop holes)
  (foreach loop (EL:Get 'regions block)
    (if (and (<= (abs (- (caddr point) (caddr (caar loop)))) (EL:GapEpsilon))
             (EL:InsideSegments point loop)) (setq hit T)))
  (foreach loop (EL:Get 'holes block)
    (if (EL:InsideSegments point loop) (setq holes T)))
  (and hit (not holes)))
(defun TEST16:BlockPointHit (point block cfg)
  (or (TEST16:Touches point (EL:Get 'segments block) (EL:Get 'eps_boundary (EL:Get 'params cfg)) (EL:GapEpsilon))
      (TEST16:RegionContains point block)))
(defun TEST16:PathBlockHit (wire block cfg / hit seg edge mid)
  (foreach seg (EL:Get 'segments wire)
    (if (or (TEST16:BlockPointHit (car seg) block cfg) (TEST16:BlockPointHit (cadr seg) block cfg)
            (TEST16:RegionContains (EL:V* 0.5 (EL:V+ (car seg) (cadr seg))) block)) (setq hit T))
    (foreach edge (EL:Get 'segments block)
      (if (and (<= (abs (- (caddr (car seg)) (caddr (car edge)))) (EL:GapEpsilon))
               (<= (abs (- (caddr (cadr seg)) (caddr (car edge)))) (EL:GapEpsilon))
               (EL:GapHitsSegment (car seg) (cadr seg) (car edge) (cadr edge))) (setq hit T))))
  hit)
(defun TEST16:BuildPhysical (snapshot cfg panel / ends out a b block contacts direct edges issues p tol ztol row other hit status ports attached id wire pathcontacts bid portcount blockedwires)
  (setq ends (EL:Get 'ends snapshot) tol (EL:Get 'eps_touch (EL:Get 'params cfg)) ztol (EL:Get 'eps_z (EL:Get 'params cfg)))
  (foreach a ends
    (EL:LogEvent "PHYSICAL_ENDPOINT" a)
    (setq contacts nil direct nil p (EL:Get 'point a) status nil)
    (foreach block (EL:Get 'blocks snapshot)
      (if (and (not (equal (EL:Get 'role block) 'ignore)) (or (TEST16:BlockPointHit p block cfg)
              (and (EL:Get 'issues block) (EL:InBounds p (EL:Get 'bounds block) (EL:Get 'eps_boundary (EL:Get 'params cfg))))))
        (progn
          (setq contacts (cons (EL:Get 'id block) contacts))
          (if (EL:Get 'issues block) (setq status 'UNVERIFIED_CONTOUR)))))
    (foreach row (EL:Get 'wires snapshot)
      (if (and (not (equal (EL:Get 'id row) (EL:Get 'wire a))) (EL:InBounds p (EL:Get 'bounds row) tol))
        (setq status 'UNSUPPORTED_WIRE_CONTACT)))
    (foreach b ends
      (if (and (not (equal (EL:Get 'wire a) (EL:Get 'wire b)))
               (EL:LayerAllowed (EL:Get 'layer a) (EL:Get 'layer b) cfg)
               (<= (abs (- (caddr p) (caddr (EL:Get 'point b)))) ztol)
               (<= (EL:Norm (EL:V- p (EL:Get 'point b))) tol)) (setq direct (cons (EL:Get 'key b) direct))))
    (cond ((> (+ (length contacts) (length direct)) 1) (setq status 'AMBIGUOUS_CONTACT))
          ((= (length contacts) 1)
           (setq block (EL:By 'id (car contacts) (EL:Get 'blocks snapshot)))
           (if (member (EL:Get 'role block) '(unknown ambiguous)) (setq status 'UNKNOWN_ROLE)))
          ((not direct)
           (foreach row (EL:Get 'wires snapshot)
             (if (not (equal (EL:Get 'id row) (EL:Get 'wire a)))
               (foreach hit (EL:Get 'segments row)
                 (if (and (<= (EL:PointSegmentDistance p (car hit) (cadr hit)) tol)
                          (not (vl-some '(lambda (endpoint) (<= (EL:Norm (EL:V- p (EL:Get 'point endpoint))) tol)) (EL:Get 'ends row))))
                   (setq status 'T_JUNCTION)))))))
    (if status (setq issues (cons (EL:Issue status (EL:Get 'wire a) (EL:Get 'key a)) issues)))
    (setq a (EL:Put 'contacts contacts a) a (EL:Put 'direct direct a)
          a (EL:Put 'occupied (or contacts direct status) a) a (EL:Put 'status status a))
    (if (and (= (length contacts) 1) (not status) (not (equal (car contacts) panel))
             (member (EL:Get 'role block) '(device panel leader)))
      (setq edges (cons (EL:Edge (EL:Get 'wire a) (car contacts)) edges)))
    (setq out (cons a out)))
  (setq ends (reverse out))
  ;; Virtual incidences attach whole paths without modifying CAD entities.
  (foreach wire (EL:Get 'wires snapshot)
    (EL:LogEvent "PHYSICAL_WIRE" (list (EL:Get 'id wire) (EL:Get 'ends wire) (EL:Get 'issues wire)))
    (foreach block (EL:Get 'blocks snapshot)
      (setq bid (EL:Get 'id block))
      (if (and (not (equal (EL:Get 'role block) 'ignore))
               (EL:BoundsOverlap (EL:SegmentBounds (EL:Get 'segments wire))
                 (cond ((EL:Get 'bounds block)) (T (EL:SegmentBounds (EL:Get 'segments block)))) tol))
        (cond
          ((TEST16:PathBlockHit wire block cfg)
            (setq pathcontacts (cons (list (EL:Get 'id wire) bid) pathcontacts))
            (if (member (EL:Get 'role block) '(device panel unknown ambiguous))
              (setq attached (EL:Put (EL:Get 'id wire) T attached)))
            (cond
              ((member (EL:Get 'role block) '(unknown ambiguous))
                (setq issues (cons (EL:Issue 'UNKNOWN_ROLE (EL:Get 'id wire) bid) issues)))
              ((equal (EL:Get 'role block) 'device)
                (setq edges (cons (EL:Edge (EL:Get 'id wire) bid) edges)))
              ((equal (EL:Get 'role block) 'panel)
                (if (not (vl-some '(lambda (ep) (member bid (EL:Get 'contacts ep)))
                          (vl-remove-if-not '(lambda (ep) (equal (EL:Get 'wire ep) (EL:Get 'id wire))) ends)))
                  (setq blockedwires (cons (EL:Get 'id wire) blockedwires)
                        issues (cons (EL:Issue 'PANEL_PATH_CROSSING (EL:Get 'id wire) bid) issues)))))
            (if (EL:Get 'issues block)
              (setq issues (cons (EL:Issue 'UNVERIFIED_CONTOUR (EL:Get 'id wire) bid) issues))))
          ((or (not (EL:Get 'regions block)) (EL:Get 'issues block))
            (setq attached (EL:Put (EL:Get 'id wire) T attached)
                  issues (cons (EL:Issue 'UNVERIFIED_REGION (EL:Get 'id wire) bid) issues)))))))
  ;; A connection at either end excludes the whole source entity from gap pairing.
  (foreach a ends
    (foreach id (EL:Get 'contacts a)
      (setq block (EL:By 'id id (EL:Get 'blocks snapshot)))
      (if (member (EL:Get 'role block) '(panel device))
        (setq attached (EL:Put (EL:Get 'wire a) T attached)))))
  (setq ends (mapcar '(lambda (e)
    (EL:Put 'wire-attached (EL:Get (EL:Get 'wire e) attached) e)) ends))
  (foreach block (EL:Get 'blocks snapshot)
    (if (equal (EL:Get 'role block) 'device)
      (progn
        (setq ports nil portcount 0)
        (foreach wire (EL:Get 'wires snapshot)
          (if (member (list (EL:Get 'id wire) (EL:Get 'id block)) pathcontacts)
            (progn
              (setq ports (cons (EL:Get 'id wire) ports))
              (setq portcount (+ portcount
                (if (vl-some '(lambda (ep) (member (EL:Get 'id block) (EL:Get 'contacts ep)))
                      (vl-remove-if-not '(lambda (ep) (equal (EL:Get 'wire ep) (EL:Get 'id wire))) ends)) 1 2))))))
        (if (> portcount 2)
          (setq issues (cons (EL:Issue 'ABNORMAL_BRANCH (EL:Get 'id block) ports) issues))))))
  (foreach a ends
    (setq b (EL:By 'key (list (EL:Get 'wire a) (if (equal (EL:Get 'side a) 'start) 'end 'start)) ends))
    (if (and b (= (length (EL:Get 'contacts a)) 1) (equal (EL:Get 'contacts a) (EL:Get 'contacts b)))
      (setq issues (cons (EL:Issue 'CLOSED_CIRCUIT (EL:Get 'wire a) (EL:Get 'contacts a)) issues))))
  (foreach a ends
    (if (and (= (length (EL:Get 'direct a)) 1) (not (EL:Get 'status a)))
      (progn
        (setq b (EL:By 'key (car (EL:Get 'direct a)) ends))
        (if (and (= (length (EL:Get 'direct b)) 1) (not (EL:Get 'status b)))
          (setq edges (cons (EL:Edge (EL:Get 'wire a) (EL:Get 'wire b)) edges))
          (setq issues (cons (EL:Issue 'AMBIGUOUS_CONTACT (EL:Get 'wire a) (EL:Get 'key b)) issues))))))
  (setq edges (vl-remove-if '(lambda (edge) (or (member (car edge) blockedwires) (member (cadr edge) blockedwires))) edges))
  (list (cons 'snapshot (EL:Put 'path-contacts (EL:Unique pathcontacts) (EL:Put 'ends ends snapshot))) (cons 'edges (EL:Unique edges)) (cons 'issues issues)))
