(defun EL:Edge (a b) (if (< a b) (list a b) (list b a)))
(defun EL:Neighbours (id edges / out e)
  (foreach e edges
    (cond ((equal id (car e)) (setq out (cons (cadr e) out)))
          ((equal id (cadr e)) (setq out (cons (car e) out))))) (EL:Unique out))
;; Date: 2026-10-14. A shared physical contact is not a second electrical route.
;; Keep exact wire/device handles; remove only a proven redundant wire edge.
(defun EL:SingleWireContactPoint (a b / pair ep point points)
  (foreach pair (list (list a b) (list b a))
    (foreach ep (EL:Get 'ends (car pair))
      (setq point (EL:Get 'point ep))
      (if (and (EL:Point point) (EL:Touches point (EL:Get 'segments (cadr pair)) (EL:GapEpsilon) (EL:GapEpsilon))
          (not (vl-some '(lambda (p) (equal p point (EL:GapEpsilon))) points)))
        (setq points (cons point points)))))
  (if (= (length points) 1) (car points)))
(defun EL:ConvexContactRegion (shape / ring points seg point value sign convex)
  ;; Bound the all-vertex proof; complex or uncertain shapes keep diagnostics.
  (setq ring (car (EL:Get 'regions shape)))
  (if (and (= (length (EL:Get 'regions shape)) 1) (not (EL:Get 'holes shape))
      (not (EL:Get 'curves shape)) (not (EL:Get 'sampled-curves shape))
      (<= 3 (length ring)) (<= (length ring) 64) (<= (length (EL:Get 'segments shape)) 64)
      (vl-every '(lambda (s) (or (member s ring) (member (reverse s) ring))) (EL:Get 'segments shape)))
    (progn
      (setq convex T points (mapcar 'car ring))
      (foreach seg ring
        (foreach point points
          (if (> (abs (- (caddr point) (caddr (caar ring)))) (EL:GapEpsilon)) (setq convex nil))
          (setq value (EL:Cross (EL:V- (cadr seg) (car seg)) (EL:V- point (car seg))))
          (if (> (abs value) (EL:GapEpsilon))
            (if sign (if (< (* sign value) 0.0) (setq convex nil)) (setq sign value)))))
      (and convex sign T))))
(defun EL:ContactGeometryBounds (shape / bounds curve center radius lo hi)
  ;; Visible geometry only. A full-circle envelope also safely covers any arc.
  (if (and (not (EL:Get 'sampled-curves shape))
      (<= (+ (length (EL:Get 'segments shape)) (length (EL:Get 'curves shape))) 256))
    (progn
      (setq bounds (EL:SegmentBounds (EL:Get 'segments shape)))
      (foreach curve (EL:Get 'curves shape)
        (setq center (car curve) radius (cadr curve)
          lo (list (- (car center) radius) (- (cadr center) radius) (caddr center))
          hi (list (+ (car center) radius) (+ (cadr center) radius) (caddr center))
          bounds (if bounds (list (mapcar 'min (car bounds) lo) (mapcar 'max (cadr bounds) hi)) (list lo hi))))
      bounds)))
(defun EL:OutsideContactEnvelope (endpoint point bounds / axis outside moved eps delta)
  (setq eps (EL:GapEpsilon))
  (if bounds
    (if (equal endpoint point eps) T
      (progn
        (setq outside T)
        ;; Every varying XY coordinate must head outward. A nearly tangential
        ;; ray could otherwise meet a remote port within the device tolerance.
        (foreach axis '(0 1)
          (setq delta (- (nth axis endpoint) (nth axis point)))
          (if (> (abs delta) eps)
            (progn
              (setq moved T)
              (if (not (or (and (< delta 0.0)
                  (<= (abs (- (nth axis point) (nth axis (car bounds)))) eps))
                (and (> delta 0.0)
                  (<= (abs (- (nth axis point) (nth axis (cadr bounds)))) eps)))) (setq outside nil)))))
        (and outside moved)))))
(defun EL:WireDeviceContactLocal (wire shape point cfg / local ep seg convex bounds cursor station previous)
  ;; A wire which returns to another port must retain its cycle evidence.
  (setq local T cursor 0.0 convex (EL:ConvexContactRegion shape)
    bounds (if (not convex) (EL:ContactGeometryBounds shape)))
  (foreach ep (EL:Get 'ends wire)
    (if (and local (not (equal point (EL:Get 'point ep) (EL:GapEpsilon)))
        (EL:ContourPointHit (EL:Get 'point ep) shape cfg)) (setq local nil)))
  (foreach seg (EL:Get 'segments wire)
    (if local
      (if (EL:Touches point (list seg) (EL:GapEpsilon) (EL:GapEpsilon))
        (progn
          ;; Distinct stations also catch immediate out-and-back visits to P.
          (setq station (+ cursor (EL:Norm (EL:V- point (car seg)))))
          (if (or (and (numberp previous) (> (abs (- station previous)) (EL:GapEpsilon)))
              (not (or convex
              (and (EL:OutsideContactEnvelope (car seg) point bounds)
                   (EL:OutsideContactEnvelope (cadr seg) point bounds))))) (setq local nil))
          (setq previous station))
        (progn
          (if (EL:ContourPathHit (list (cons 'segments (list seg))) shape cfg) (setq local nil)))))
    (setq cursor (+ cursor (EL:Norm (EL:V- (cadr seg) (car seg))))))
  local)
(defun EL:NormalizeContactEdges (snapshot edges cfg / wires blocks gaps row edge a b point neighbours id block shape drop out contactcfg)
  (foreach row (EL:Get 'wires snapshot) (setq wires (cons (cons (EL:Get 'id row) row) wires)))
  (foreach row (EL:Get 'blocks snapshot) (setq blocks (cons (cons (EL:Get 'id row) row) blocks)))
  ;; A pair can have both a local physical join and a remote virtual return.
  (foreach row (EL:Get 'gap-pairs snapshot)
    (setq gaps (cons (EL:Edge (car (EL:Get 'a row)) (car (EL:Get 'b row))) gaps)))
  (setq contactcfg (EL:Put 'params (EL:Put 'eps_boundary (EL:DeviceContactTolerance cfg)
    (EL:Get 'params cfg)) cfg))
  (foreach edge edges
    (setq drop nil a (cdr (assoc (car edge) wires)) b (cdr (assoc (cadr edge) wires)))
    (if (and a b (not (member edge gaps)) (not (EL:Get 'issues a)) (not (EL:Get 'issues b))
        (setq point (EL:SingleWireContactPoint a b)))
      (progn
        (setq neighbours (EL:Neighbours (EL:Get 'id b) edges))
        (foreach id (EL:Neighbours (EL:Get 'id a) edges)
          (if (and (not drop) (member id neighbours)
              (setq block (cdr (assoc id blocks))) (equal (EL:Get 'role block) 'device))
            (progn
              (setq shape (EL:DeviceContactShape block))
              (if (and (EL:ShapeGeometry shape) (not (EL:Get 'issues shape))
                  (EL:ContourPointHit point shape contactcfg)
                  (EL:WireDeviceContactLocal a shape point contactcfg)
                  (EL:WireDeviceContactLocal b shape point contactcfg))
                (progn
                  (setq drop T)
                  (EL:LogEvent "CONTACT_JUNCTION_NORMALIZED"
                    (list (cons 'wires edge) (cons 'device id) (cons 'point point))))))))))
    (if (not drop) (setq out (cons edge out))))
  (reverse out))
(defun EL:ComponentIndex (edges / rows edge serial sorted id neighbours groups *EL:ComponentCursor*)
  ;; Date: 2026-10-13. Sort directed rows once, then build a balanced lookup.
  ;; Edge ordinal preserves the original reverse-edge neighbour visit order.
  (setq serial 0)
  (foreach edge edges
    (setq rows (cons (list (car edge) (cadr edge) serial) rows))
    (if (not (equal (car edge) (cadr edge)))
      (setq rows (cons (list (cadr edge) (car edge) serial) rows)))
    (setq serial (1+ serial)))
  (setq sorted (vl-sort rows '(lambda (a b)
    (if (equal (car a) (car b)) (> (caddr a) (caddr b)) (< (car a) (car b))))))
  (foreach edge sorted
    (if (and id (not (equal id (car edge))))
      (setq groups (cons (cons id (EL:Unique (reverse neighbours))) groups) neighbours nil))
    (setq id (car edge) neighbours (cons (cadr edge) neighbours)))
  (if id (setq groups (cons (cons id (EL:Unique (reverse neighbours))) groups)))
  (setq *EL:ComponentCursor* (reverse groups))
  (EL:PerfCount "component-index-builds" 1)
  (EL:PerfCount "component-edge-scans" serial)
  (EL:ComponentIndexTake (length groups)))
(defun EL:ComponentIndexTake (count / middle left row right)
  (if (> count 0)
    (progn
      (setq middle (/ count 2) left (EL:ComponentIndexTake middle)
        row (car *EL:ComponentCursor*) *EL:ComponentCursor* (cdr *EL:ComponentCursor*)
        right (EL:ComponentIndexTake (- count middle 1)))
      (list row left right))))
(defun EL:ComponentNeighbours (id tree)
  (if tree
    (cond ((equal id (caar tree)) (cdar tree))
      ((< id (caar tree)) (EL:ComponentNeighbours id (cadr tree)))
      (T (EL:ComponentNeighbours id (caddr tree))))))
(defun EL:Component (start edges / queue visited id next index)
  ;; Small or non-handle graphs retain the general-purpose original path.
  (if (and (> (length edges) 32) (equal (type start) 'STR)
      (vl-every '(lambda (edge) (and (equal (type (car edge)) 'STR)
        (equal (type (cadr edge)) 'STR))) edges))
    (setq index (EL:PerfCall "COMPONENT_INDEX" 'EL:ComponentIndex (list edges))))
  (setq queue (list start))
  (while queue
    (setq id (car queue) queue (cdr queue))
    (if (not (member id visited))
      (progn
        (setq visited (cons id visited))
        (if index (EL:PerfCount "component-index-lookups" 1)
          (EL:PerfCount "component-edge-scans" (length edges)))
        (foreach next (if index (EL:ComponentNeighbours id index) (EL:Neighbours id edges))
          (if (not (member next visited)) (setq queue (cons next queue))))))) (EL:Unique visited))
(defun EL:InsideSegments (p segments / count seg a b x)
  (setq count 0)
  (foreach seg segments
    (setq a (car seg) b (cadr seg))
    (if (or (and (> (cadr a) (cadr p)) (<= (cadr b) (cadr p)))
            (and (> (cadr b) (cadr p)) (<= (cadr a) (cadr p))))
      (progn
        (setq x (+ (car a) (* (- (cadr p) (cadr a)) (/ (- (car b) (car a)) (- (cadr b) (cadr a))))))
        (if (> x (car p)) (setq count (1+ count)))))) (= 1 (rem count 2)))
(defun EL:SeedCandidates (snapshot cfg panel / block seeds wire ep i)
  (setq block (EL:By 'id panel (EL:Get 'blocks snapshot)))
  (if (EL:Get 'whole-block block)
    (progn
      (setq i 0)
      (foreach wire (vl-sort (EL:Get 'wires snapshot)
          '(lambda (a b) (< (EL:Get 'id a) (EL:Get 'id b))))
        (if (member (list (EL:Get 'id wire) panel) (EL:Get 'path-contacts snapshot))
          (progn
            (setq i (1+ i) ep (car (EL:Get 'ends wire)))
            (setq seeds (cons (list (cons 'id (strcat "R" (itoa i)))
              (cons 'wire (EL:Get 'id wire)) (cons 'key (EL:Get 'key ep))
              (cons 'point (EL:Get 'point ep))) seeds)))))
      (reverse seeds))
    (EL:ContourSeedCandidates snapshot cfg panel)))
(defun EL:ContourSeedCandidates (snapshot cfg panel / block ends seeds endrec id i wire direction step)
  (setq block (EL:By 'id panel (EL:Get 'blocks snapshot)) ends (EL:Get 'ends snapshot) i 0)
  (foreach endrec (vl-sort ends '(lambda (a b) (< (EL:Signature (EL:Get 'key a)) (EL:Signature (EL:Get 'key b)))))
    (if (and (equal (EL:Get 'contacts endrec) (list panel)) (not (EL:Get 'status endrec)))
      (progn
        (setq direction (EL:Get 'direction endrec)
              step (max 0.001 (* 3.0 (EL:Get 'eps_boundary (EL:Get 'params cfg)))))
        (if (and direction (not (EL:InsideSegments
          (EL:V- (EL:Get 'point endrec) (EL:V* step direction)) (EL:Get 'segments block))))
          (progn
            (setq i (1+ i))
            (setq seeds (cons (list (cons 'id (strcat "R" (itoa i))) (cons 'wire (EL:Get 'wire endrec))
              (cons 'key (EL:Get 'key endrec)) (cons 'point (EL:Get 'point endrec))) seeds)))))))
  (reverse seeds))
(defun EL:ValidatePairSet (snapshot cfg base pairs seeds / good issues counts pair a b key invalid temp component seed hits rejected accepted rec objects)
  ;; Validate all proposals before traversal. Reject every proposal in a conflict component.
  (foreach pair pairs
    (setq a (EL:By 'key (EL:Get 'a pair) (EL:Get 'ends snapshot))
          b (EL:By 'key (EL:Get 'b pair) (EL:Get 'ends snapshot)))
    (if (and a b (not (EL:Get 'occupied a)) (not (EL:Get 'occupied b))
             (not (EL:Get 'wire-attached a)) (not (EL:Get 'wire-attached b))
             (not (equal (EL:Get 'wire a) (EL:Get 'wire b)))
             (not (equal (EL:Get 'geometry a) 'INVALID_GEOMETRY)) (not (equal (EL:Get 'geometry b) 'INVALID_GEOMETRY))
             (EL:LayerAllowed (EL:Get 'layer a) (EL:Get 'layer b) cfg)
             (<= (abs (- (caddr (EL:Get 'point a)) (caddr (EL:Get 'point b)))) (EL:Get 'eps_z (EL:Get 'params cfg))))
      (progn
        (setq good (cons pair good))
        (foreach key (list (EL:Get 'a pair) (EL:Get 'b pair))
          (setq counts (EL:Put key (1+ (cond ((EL:Get key counts)) (T 0))) counts))))
      (foreach rec (list (car (EL:Get 'a pair)) (car (EL:Get 'b pair)))
        (setq issues (cons (EL:Issue 'ENDPOINT_OCCUPIED rec pair) issues)))))
  (foreach pair good
    (if (or (> (EL:Get (EL:Get 'a pair) counts) 1) (> (EL:Get (EL:Get 'b pair) counts) 1))
      (progn
        (setq rejected (cons pair rejected))
        (foreach rec (list (car (EL:Get 'a pair)) (car (EL:Get 'b pair)))
          (setq issues (cons (EL:Issue 'ENDPOINT_OCCUPIED rec pair) issues))))))
  (setq temp base)
  (foreach pair good
    (if (not (member pair rejected))
      (setq temp (cons (EL:Edge (car (EL:Get 'a pair)) (car (EL:Get 'b pair))) temp))))
  (foreach seed seeds
    (setq component (EL:Component (EL:Get 'wire seed) temp) hits nil)
    (foreach rec seeds (if (member (EL:Get 'wire rec) component) (setq hits (cons (EL:Get 'id rec) hits))))
    (if (> (length hits) 1)
      (progn
        (foreach rec component (setq issues (cons (EL:Issue 'CIRCUIT_CONFLICT rec (vl-sort (EL:Unique hits) '<)) issues)))
        (foreach pair good
          (if (member (car (EL:Get 'a pair)) component) (setq rejected (cons pair rejected)))))))
  (setq temp base)
  (foreach pair good
    (if (not (member pair rejected))
      (setq accepted (cons pair accepted) temp (cons (EL:Edge (car (EL:Get 'a pair)) (car (EL:Get 'b pair))) temp))))
  (list (cons 'pairs accepted) (cons 'edges (EL:Unique temp)) (cons 'issues (EL:Unique issues))))
(defun EL:LeaderConnections (snapshot cfg base / edges issues used pair a b valid block id rec counts)
  (setq edges base)
  (foreach pair (EL:Get 'leader-pairs cfg)
    (foreach id (list (EL:Get 'a pair) (EL:Get 'b pair))
      (setq counts (EL:Put id (1+ (cond ((EL:Get id counts)) (T 0))) counts))))
  (foreach pair (EL:Get 'leader-pairs cfg)
    (setq a (EL:By 'id (EL:Get 'a pair) (EL:Get 'blocks snapshot))
          b (EL:By 'id (EL:Get 'b pair) (EL:Get 'blocks snapshot)))
    (if (and a b (equal (EL:Get 'role a) 'leader) (equal (EL:Get 'role b) 'leader)
             (not (equal (EL:Get 'id a) (EL:Get 'id b)))
             (equal (EL:Get 'a-state pair) (EL:Get 'raw a)) (equal (EL:Get 'b-state pair) (EL:Get 'raw b))
             (= (EL:Get (EL:Get 'id a) counts) 1) (= (EL:Get (EL:Get 'id b) counts) 1)
             (not (member (EL:Get 'id a) used)) (not (member (EL:Get 'id b) used)))
      (progn
        (setq used (append used (list (EL:Get 'id a) (EL:Get 'id b)))
              edges (cons (EL:Edge (EL:Get 'id a) (EL:Get 'id b)) edges))
        (foreach rec (list a b)
          (if (/= (length (EL:Neighbours (EL:Get 'id rec) base)) 1)
            (setq issues (cons (EL:Issue 'LEADER_PORTS (EL:Get 'id rec) nil) issues)))))
      (foreach id (list (EL:Get 'a pair) (EL:Get 'b pair))
        (setq issues (cons (EL:Issue 'STALE_LEADER_PAIR id pair) issues)))))
  (foreach block (EL:Get 'blocks snapshot)
    (if (and (equal (EL:Get 'role block) 'leader) (not (member (EL:Get 'id block) used)))
      (setq issues (cons (EL:Issue 'UNPAIRED_LEADER (EL:Get 'id block) nil) issues))))
  (list (cons 'edges (EL:Unique edges)) (cons 'issues issues)))
(defun EL:MergePairs (manual automatic / pairs issues claims pair key same)
  (setq pairs manual)
  (foreach pair manual (setq claims (append claims (list (EL:Get 'a pair) (EL:Get 'b pair)))))
  (foreach pair automatic
    (setq same (vl-some '(lambda (m) (or (and (equal (EL:Get 'a m) (EL:Get 'a pair)) (equal (EL:Get 'b m) (EL:Get 'b pair)))
      (and (equal (EL:Get 'b m) (EL:Get 'a pair)) (equal (EL:Get 'a m) (EL:Get 'b pair))))) manual))
    (cond (same nil)
          ((or (member (EL:Get 'a pair) claims) (member (EL:Get 'b pair) claims))
           (foreach key (list (EL:Get 'a pair) (EL:Get 'b pair))
             (setq issues (cons (EL:Issue 'ENDPOINT_OCCUPIED (car key) pair) issues))))
          (T (setq pairs (cons pair pairs)))))
  (list (cons 'pairs pairs) (cons 'issues issues)))
(defun EL:AnalyzeSnapshot (snapshot cfg panel seeds / physical leaders manual rows automatic merged checked issues resolved pair issue circuits circuit seed allobjects orphan portissues endrec other shared updated conflict started physical-ms candidate-start candidate-ms trace-start)
  (setq started (EL:Tick) physical (EL:BuildPhysical snapshot cfg panel) physical-ms (EL:Elapsed started) snapshot (EL:Get 'snapshot physical)
        leaders (EL:LeaderConnections snapshot cfg (EL:Get 'edges physical))
        manual (EL:LoadValidGapPairs cfg snapshot) candidate-start (EL:Tick) rows (EL:FindGapCandidates snapshot cfg)
        candidate-ms (EL:Elapsed candidate-start) trace-start (EL:Tick)
        automatic (EL:BuildMutualPairs rows snapshot cfg)
        merged (EL:MergePairs (EL:Get 'pairs manual) (EL:Get 'pairs automatic))
        checked (EL:ValidatePairSet snapshot cfg (EL:Get 'edges leaders) (EL:Get 'pairs merged) seeds)
        issues (append (EL:Get 'issues physical) (EL:Get 'issues leaders) (EL:Get 'issues manual)
          (EL:Get 'issues automatic) (EL:Get 'issues merged) (EL:Get 'issues checked)))
  (foreach pair (EL:Get 'pairs checked) (setq resolved (append resolved (list (EL:Get 'a pair) (EL:Get 'b pair)))))
  (setq issues (vl-remove-if '(lambda (i) (and (member (EL:Get 'code i)
      '(NO_CANDIDATE AMBIGUOUS_CANDIDATES NOT_MUTUALLY_UNIQUE UNSUPPORTED_END_GEOMETRY))
      (member (EL:Get 'key (EL:Get 'detail i)) resolved))) issues))
  (foreach seed seeds
    (setq circuit (EL:TraceCircuit seed snapshot (EL:Get 'edges checked) issues)
          circuits (cons circuit circuits) allobjects (append allobjects (EL:Get 'objects circuit))))
  (foreach circuit circuits
    (setq shared nil)
    (foreach other circuits
      (if (not (equal (EL:Get 'id circuit) (EL:Get 'id other)))
        (foreach conflict (EL:Get 'objects circuit)
          (if (member conflict (EL:Get 'objects other)) (setq shared (cons conflict shared))))))
    (if shared
      (setq circuit (EL:Put 'complete nil (EL:Put 'issues
        (cons (EL:Issue 'CIRCUIT_OWNERSHIP_CONFLICT (EL:Get 'id circuit) (EL:Unique shared)) (EL:Get 'issues circuit)) circuit))))
    (setq updated (cons circuit updated)))
  (setq circuits (reverse updated))
  (foreach issue (append issues (EL:Get 'issues snapshot))
    (if (not (member (EL:Get 'object issue) allobjects)) (setq orphan (cons issue orphan))))
  (foreach endrec (EL:Get 'ends snapshot)
    (if (and (member panel (EL:Get 'contacts endrec)) (or (EL:Get 'status endrec) (not (EL:Get 'direction endrec))))
      (setq portissues (cons (EL:Issue 'PANEL_PORT_AMBIGUOUS (EL:Get 'wire endrec) endrec) portissues))))
  (list (cons 'drawing (EL:Get 'drawing cfg)) (cons 'panel panel) (cons 'snapshot snapshot) (cons 'rules (EL:RecognitionRules cfg))
        (cons 'timing (append (EL:Get 'timing snapshot) (list (cons 'physical-ms physical-ms)
          (cons 'candidates-ms candidate-ms) (cons 'trace-and-validation-ms (EL:Elapsed trace-start)))))
        (cons 'config-revision (EL:Get 'revision cfg)) (cons 'circuits (reverse circuits))
        (cons 'connections (EL:Get 'pairs checked)) (cons 'candidates rows)
        (cons 'issues (append portissues issues)) (cons 'unrelated-issues (EL:Unique orphan))
        (cons 'complete (and seeds (not portissues) (not (vl-some '(lambda (c) (not (EL:Get 'complete c))) circuits))))))
(defun EL:PhysicalProgress (phase completed total started object)
  (EL:LogEvent "PHYSICAL_PROGRESS" (list (cons 'phase phase) (cons 'completed completed)
    (cons 'total total) (cons 'elapsed-ms (EL:Elapsed started)) (cons 'object object)))
  (if *EL:LogActive*
    (vl-catch-all-apply 'grtext (list -1 (strcat "接线检查 " phase " " (itoa completed) "/" (itoa total)))))
  nil)
(defun EL:BuildPhysical (snapshot cfg panel / ends out a b block contacts direct edges issues p tol ztol row other hit status ports attached id wire pathcontacts bid blockedwires blocks wirebounds started itemstarted completed total)
  (setq ends (EL:Get 'ends snapshot) tol (EL:Get 'eps_touch (EL:Get 'params cfg)) ztol (EL:Get 'eps_z (EL:Get 'params cfg)))
  (setq started (EL:Tick) completed 0 total (length (EL:Get 'blocks snapshot)))
  (EL:PhysicalProgress "index" 0 total started nil)
  (foreach block (EL:Get 'blocks snapshot)
    (setq blocks (cons (if (equal (EL:Get 'role block) 'ignore) block
      (EL:LogCall "CONTACT_INDEX" (list (EL:Get 'id block) (length (EL:Get 'segments block)))
        'EL:PrepareContactBlock (list block))) blocks) completed (1+ completed)))
  (setq blocks (reverse blocks))
  (EL:PhysicalProgress "index" completed total started nil)
  (setq completed 0 total (length ends))
  (foreach a ends
    (EL:LogEvent "PHYSICAL_ENDPOINT" a)
    (setq contacts nil direct nil p (EL:Get 'point a) status nil itemstarted (EL:Tick))
    (foreach block blocks
      (if (and (not (equal (EL:Get 'role block) 'ignore)) (or (EL:BlockPointHit p block cfg)
              (and (EL:Get 'issues block) (EL:InBounds p (EL:Get 'bounds block) (EL:Get 'eps_boundary (EL:Get 'params cfg))))))
        (progn
          (setq contacts (cons (EL:Get 'id block) contacts))
          (if (EL:Get 'issues block) (setq status 'UNVERIFIED_CONTOUR)))))
    (foreach row (EL:Get 'wires snapshot)
      (if (and (not (equal (EL:Get 'id row) (EL:Get 'wire a))) (EL:InBounds p (EL:Get 'bounds row) tol))
        (setq status 'UNSUPPORTED_WIRE_CONTACT)))
    (foreach b ends
      (if (and (not (equal (EL:Get 'wire a) (EL:Get 'wire b)))
               (EL:LayerAllowed (EL:Get 'layer a) (EL:Get 'layer b) cfg)
               (<= (abs (- (caddr p) (caddr (EL:Get 'point b)))) ztol)
               (<= (EL:Norm (EL:V- p (EL:Get 'point b))) tol)) (setq direct (cons (EL:Get 'key b) direct))))
    (cond ((> (+ (length contacts) (length direct)) 1) (setq status 'AMBIGUOUS_CONTACT))
          ((= (length contacts) 1)
           (setq block (EL:By 'id (car contacts) blocks))
           (if (member (EL:Get 'role block) '(unknown ambiguous)) (setq status 'UNKNOWN_ROLE)))
          ((not direct)
           (foreach row (EL:Get 'wires snapshot)
             (if (not (equal (EL:Get 'id row) (EL:Get 'wire a)))
               (foreach hit (EL:Get 'segments row)
                 (if (and (<= (EL:PointSegmentDistance p (car hit) (cadr hit)) tol)
                          (not (vl-some '(lambda (endpoint) (<= (EL:Norm (EL:V- p (EL:Get 'point endpoint))) tol)) (EL:Get 'ends row))))
                   (setq status 'T_JUNCTION)))))))
    (if status (setq issues (cons (EL:Issue status (EL:Get 'wire a) (EL:Get 'key a)) issues)))
    (setq a (EL:Put 'contacts contacts a) a (EL:Put 'direct direct a)
          a (EL:Put 'occupied (or contacts direct status) a) a (EL:Put 'status status a))
    (if (and (= (length contacts) 1) (not status) (not (equal (car contacts) panel))
             (member (EL:Get 'role block) '(device panel leader)))
      (setq edges (cons (EL:Edge (EL:Get 'wire a) (car contacts)) edges)))
    (setq out (cons a out) completed (1+ completed))
    (EL:LogEvent "PHYSICAL_ENDPOINT_DONE" (list (EL:Get 'key a) (cons 'elapsed-ms (EL:Elapsed itemstarted))))
    (if (= (rem completed 8) 0) (EL:PhysicalProgress "endpoints" completed total started (EL:Get 'key a))))
  (EL:PhysicalProgress "endpoints" completed total started nil)
  (setq ends (reverse out))
  ;; Virtual incidences attach whole paths without modifying CAD entities.
  (setq completed 0 total (length (EL:Get 'wires snapshot)))
  (foreach wire (EL:Get 'wires snapshot)
    (EL:LogEvent "PHYSICAL_WIRE" (list (EL:Get 'id wire) (EL:Get 'ends wire) (EL:Get 'issues wire)))
    (setq wirebounds (EL:SegmentBounds (EL:Get 'segments wire)))
    (foreach block blocks
      (setq bid (EL:Get 'id block))
      (if (and (not (equal (EL:Get 'role block) 'ignore))
               (EL:BoundsOverlap wirebounds (EL:Get 'contact-path-bounds block) tol))
        (cond
          ((EL:LogCall "PHYSICAL_PATH_CHECK" (list (cons 'wire (EL:Get 'id wire)) (cons 'block bid)
              (cons 'wire-segments (length (EL:Get 'segments wire))) (cons 'block-segments (length (EL:Get 'segments block))))
              'EL:PathBlockHit (list wire block cfg))
            (setq pathcontacts (cons (list (EL:Get 'id wire) bid) pathcontacts))
            (if (member (EL:Get 'role block) '(device panel unknown ambiguous))
              (setq attached (EL:Put (EL:Get 'id wire) T attached)))
            (cond
              ((member (EL:Get 'role block) '(unknown ambiguous))
                (setq issues (cons (EL:Issue 'UNKNOWN_ROLE (EL:Get 'id wire) bid) issues)))
              ((equal (EL:Get 'role block) 'device)
                (setq edges (cons (EL:Edge (EL:Get 'id wire) bid) edges)))
              ((and (EL:Get 'whole-block block) (member (EL:Get 'role block) '(panel leader)))
                (if (not (equal bid panel))
                  (setq edges (cons (EL:Edge (EL:Get 'id wire) bid) edges))))
              ((equal (EL:Get 'role block) 'panel)
                (if (not (vl-some '(lambda (ep) (member bid (EL:Get 'contacts ep)))
                          (vl-remove-if-not '(lambda (ep) (equal (EL:Get 'wire ep) (EL:Get 'id wire))) ends)))
                  (setq blockedwires (cons (EL:Get 'id wire) blockedwires)
                        issues (cons (EL:Issue 'PANEL_PATH_CROSSING (EL:Get 'id wire) bid) issues)))))
            (if (EL:Get 'issues block)
              (setq issues (cons (EL:Issue 'UNVERIFIED_CONTOUR (EL:Get 'id wire) bid) issues))))
          ((and (not (EL:Get 'whole-block block)) (or (not (EL:Get 'regions block)) (EL:Get 'issues block)))
            (setq attached (EL:Put (EL:Get 'id wire) T attached)
                  issues (cons (EL:Issue 'UNVERIFIED_REGION (EL:Get 'id wire) bid) issues))))))
    (setq completed (1+ completed))
    (EL:PhysicalProgress "paths" completed total started (EL:Get 'id wire)))
  ;; A connection at either end excludes the whole source entity from gap pairing.
  (foreach a ends
    (foreach id (EL:Get 'contacts a)
      (setq block (EL:By 'id id blocks))
      (if (member (EL:Get 'role block) '(panel device))
        (setq attached (EL:Put (EL:Get 'wire a) T attached)))))
  (setq ends (mapcar '(lambda (e)
    (EL:Put 'wire-attached (EL:Get (EL:Get 'wire e) attached) e)) ends))
  ;; Date: 2026-10-09. Verified device contacts may form normal multi-wire branches.
  (foreach a ends
    (setq b (EL:By 'key (list (EL:Get 'wire a) (if (equal (EL:Get 'side a) 'start) 'end 'start)) ends))
    (if (and b (= (length (EL:Get 'contacts a)) 1) (equal (EL:Get 'contacts a) (EL:Get 'contacts b)))
      (setq issues (cons (EL:Issue 'CLOSED_CIRCUIT (EL:Get 'wire a) (EL:Get 'contacts a)) issues))))
  (foreach a ends
    (if (and (= (length (EL:Get 'direct a)) 1) (not (EL:Get 'status a)))
      (progn
        (setq b (EL:By 'key (car (EL:Get 'direct a)) ends))
        (if (and (= (length (EL:Get 'direct b)) 1) (not (EL:Get 'status b)))
          (setq edges (cons (EL:Edge (EL:Get 'wire a) (EL:Get 'wire b)) edges))
          (setq issues (cons (EL:Issue 'AMBIGUOUS_CONTACT (EL:Get 'wire a) (EL:Get 'key b)) issues))))))
  (setq edges (vl-remove-if '(lambda (edge) (or (member (car edge) blockedwires) (member (cadr edge) blockedwires))) edges))
  (list (cons 'snapshot (EL:Put 'path-contacts (EL:Unique pathcontacts) (EL:Put 'ends ends snapshot))) (cons 'edges (EL:Unique edges)) (cons 'issues issues)))
(defun EL:BuildMutualPairs (rows snapshot cfg / pairs issues row cs target other rec a b state end-index row-index)
  ;; Date: 2026-10-13. Native key lookup replaces a full interpreted endpoint
  ;; scan per row. Cons order preserves EL:By's last-record-wins semantics.
  (foreach a (EL:Get 'ends snapshot)
    (setq end-index (cons (cons (EL:Get 'key a) a) end-index)))
  (foreach row rows
    (setq row-index (cons (cons (EL:Get 'key row) row) row-index)))
  (foreach row rows
    (setq a (cdr (assoc (EL:Get 'key row) end-index)) cs (EL:Get 'candidates row))
    (if (not (EL:Get 'occupied a))
      (progn
        (setq state nil)
        (cond ((EL:Get 'wire-attached a) (setq state 'WIRE_ATTACHED_TO_EQUIPMENT))
              ((not (equal (EL:Get 'geometry a) 'straight)) (setq state (EL:Get 'geometry a)))
              ((not cs) (setq state 'NO_CANDIDATE))
              ((> (length cs) 1) (setq state 'AMBIGUOUS_CANDIDATES))
              (T
               (setq target (EL:Get 'target (car cs)) other (cdr (assoc target row-index)))
               (if (and (= (length (EL:Get 'candidates other)) 1)
                        (equal (EL:Get 'target (car (EL:Get 'candidates other))) (EL:Get 'key row)))
                 (progn
                   (setq rec (list (cons 'a (EL:Get 'key row)) (cons 'b target) (cons 'source 'auto)
                     (cons 'metrics (car cs)) (cons 'params (EL:Get 'params cfg)) (cons 'signature (EL:Get 'signature snapshot))))
                   (if (< (EL:Signature (EL:Get 'key row)) (EL:Signature target)) (setq pairs (cons rec pairs))))
                 (setq state 'NOT_MUTUALLY_UNIQUE))))
        (if state (setq issues (cons (EL:Issue state (EL:Get 'wire a) row) issues))))))
  (list (cons 'pairs pairs) (cons 'issues issues)))
;; Date: 2026-10-22. Extra graph evidence is opt-in for the read-only cold probe.
(defun EL:TraceDiagnosticHead (items limit / out)
  (repeat limit (if items (setq out (cons (car items) out) items (cdr items))))
  (reverse out))
(defun EL:TraceDiagnosticPath (id parents / path seen)
  (while (and id (not (member id seen)) (< (length path) 32))
    (setq path (cons id path) seen (cons id seen) id (cdr (assoc id parents))))
  (list (cons 'nodes path) (cons 'truncated (if id T nil))))
(defun EL:TraceDiagnosticObject (id snapshot / wire block segments)
  ;; Read only the already acquired snapshot; no new CAD/COM or geometry calls.
  (setq wire (EL:By 'id id (EL:Get 'wires snapshot))
    block (EL:By 'id id (EL:Get 'blocks snapshot))
    segments (EL:Get 'segments (cond (block) (T wire))))
  (list (cons 'handle id) (cons 'kind (if block 'block 'wire))
    (cons 'role (EL:Get 'role block)) (cons 'name (EL:Get 'name block))
    (cons 'layer (EL:Get 'layer (cond (block) (T wire))))
    (cons 'bounds (EL:Get 'bounds (cond (block) (T wire))))
    (cons 'ends (EL:TraceDiagnosticHead (EL:Get 'ends wire) 2))
    (cons 'segment-count (length segments)) (cons 'segments (EL:TraceDiagnosticHead segments 8))
    (cons 'segments-truncated (> (length segments) 8))))
(defun EL:TraceClosedDiagnostic (seed snapshot edges id parent next parents / from-neighbours to-neighbours)
  (if *EL:TraceDiagnostics*
    (if (< (cond (*EL:TraceDiagnosticCount*) (T 0)) 20)
      (progn
        (setq *EL:TraceDiagnosticCount* (1+ (cond (*EL:TraceDiagnosticCount*) (T 0)))
          from-neighbours (EL:Neighbours id edges) to-neighbours (EL:Neighbours next edges))
        (EL:LogEvent "CIRCUIT_CLOSED_EDGE" (list '(diagnostic-revision . "2026-10-22-legacy2")
          (cons 'circuit (EL:Get 'id seed)) (cons 'seed (EL:Get 'wire seed))
          '(reason . visited-non-parent-edge) (cons 'from id) (cons 'to next) (cons 'parent parent)
          (cons 'from-path (EL:TraceDiagnosticPath id parents))
          (cons 'to-path (EL:TraceDiagnosticPath next parents))
          (cons 'from-neighbour-count (length from-neighbours))
          (cons 'to-neighbour-count (length to-neighbours))
          (cons 'from-neighbours (EL:TraceDiagnosticHead from-neighbours 16))
          (cons 'to-neighbours (EL:TraceDiagnosticHead to-neighbours 16))
          (cons 'from-object (EL:TraceDiagnosticObject id snapshot))
          (cons 'to-object (EL:TraceDiagnosticObject next snapshot)))))
      (setq *EL:TraceDiagnosticOmitted* (1+ (cond (*EL:TraceDiagnosticOmitted*) (T 0)))))))
(defun EL:TraceCircuit (seed snapshot edges issues / queue visited devices wires problems step id parent neighbours next block endrec rec parents)
  (setq queue (list (list (EL:Get 'wire seed) nil)))
  (while queue
    (setq step (car queue) queue (cdr queue) id (car step) parent (cadr step))
    (if (not (member id visited))
      (progn
        (setq visited (cons id visited) block (EL:By 'id id (EL:Get 'blocks snapshot)))
        (if *EL:TraceDiagnostics* (setq parents (cons (cons id parent) parents)))
        (if block
          (cond ((equal (EL:Get 'role block) 'device) (setq devices (cons id devices)))
                ((equal (EL:Get 'role block) 'panel) (setq problems (cons (EL:Issue 'OTHER_PANEL id nil) problems)))
                ((member (EL:Get 'role block) '(unknown ambiguous))
                 (setq problems (cons (EL:Issue 'UNKNOWN_ROLE id nil) problems))))
          (setq wires (cons id wires)))
        (setq neighbours (if (and (or (not block) (member (EL:Get 'role block) '(device leader junction)))
          (not (and block (vl-some '(lambda (i) (and (equal (EL:Get 'object i) id) (equal (EL:Get 'code i) 'ABNORMAL_BRANCH))) issues))))
          (EL:Neighbours id edges)))
        (if (and block (not (member (EL:Get 'role block) '(device junction))) (> (length neighbours) 2)) (setq problems (cons (EL:Issue 'ABNORMAL_BRANCH id neighbours) problems)))
        (if (and block (equal (EL:Get 'role block) 'junction) (< (length neighbours) 2))
          (setq problems (cons (EL:Issue 'JUNCTION_INCOMPLETE id neighbours) problems)))
        (foreach next neighbours
          (if (not (equal next parent))
            (if (member next visited)
              (progn
                (setq problems (cons (EL:Issue 'CLOSED_CIRCUIT id next) problems))
                (EL:TraceClosedDiagnostic seed snapshot edges id parent next parents))
              (setq queue (append queue (list (list next id))))))))))
  (foreach rec (append (EL:Get 'issues snapshot) issues)
    (if (member (EL:Get 'object rec) visited) (setq problems (cons rec problems))))
  (list (cons 'id (EL:Get 'id seed)) (cons 'seed seed) (cons 'wires (EL:Unique wires))
        (cons 'devices (EL:Unique devices)) (cons 'objects (EL:Unique visited))
        (cons 'issues (EL:Unique problems)) (cons 'complete (not problems))))
(princ)
