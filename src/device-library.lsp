;; Date: 2026-10-11. Independent catalog. Never LOAD/EVAL user data.
(defun EL:DLFail (message)
  (setq *EL:DLError* message) nil)
(defun EL:DLNameKey (name)
  (if (and (equal (type name) 'STR) (/= (vl-string-trim " \t\r\n" name) "")) (strcase name)))
(defun EL:DLToken (text / good c)
  (setq good (and (equal (type text) 'STR) (> (strlen text) 0) (<= (strlen text) 96)))
  (if good
    (foreach c (vl-string->list text)
      (if (not (or (and (>= c 48) (<= c 57)) (and (>= c 65) (<= c 90))
          (and (>= c 97) (<= c 122)) (member c '(45 95)))) (setq good nil)))) good)
(defun EL:DLInt (value)
  (and (equal (type value) 'INT) (>= value 0) (<= value 2147483647)))
(defun EL:DLBoolField (key data)
  (and (assoc key data) (member (EL:Get key data) '(T nil))))
(defun EL:DLEntryNames (entry / names alias)
  (setq names (list (EL:Get 'block-name entry)))
  (foreach alias (EL:Get 'aliases entry) (setq names (cons alias names))) (reverse names))
(defun EL:DLAssetPrefix (entry)
  (strcat "assets/" (EL:Get 'device-id entry) "/" (itoa (EL:Get 'asset-revision entry)) "/"))
(defun EL:DLEntryAssets (entry / size)
  (setq size (EL:Get 'legend-size entry))
  (and (EL:DLToken (EL:Get 'device-id entry))
    (EL:DLInt (EL:Get 'asset-revision entry)) (> (EL:Get 'asset-revision entry) 0)
    (member (EL:Get 'block-file entry) (list (strcat (EL:DLAssetPrefix entry) "block.dwg")
      (strcat (EL:DLAssetPrefix entry) "block.dxf")))
    (equal (EL:Get 'legend-file entry) (strcat (EL:DLAssetPrefix entry) "legend.sld"))
    (EL:DLToken (EL:Get 'legend-checksum entry))
    (listp size) (= (length size) 2) (vl-every '(lambda (n) (and (EL:DLInt n) (> n 0))) size)))
(defun EL:DLEntryReady (entry)
  (and (EL:DLNameKey (EL:Get 'block-name entry))
    (EL:DLNameKey (EL:Get 'display entry)) (EL:DLInt (EL:Get 'watts entry))
    (or (> (EL:Get 'watts entry) 0) (equal (EL:Get 'zero-confirmed entry) T))
    (equal (EL:Get 'ground-confirmed entry) T) (EL:DLBoolField 'is-ground entry)
    (EL:DLEntryAssets entry)))
(defun EL:DLEntryValid (entry / ok names name key seen)
  (setq ok (and (EL:OnlyKeys entry '(device-id revision block-name aliases display watts zero-confirmed
      is-ground ground-confirmed active status asset-revision block-file legend-file legend-size legend-checksum))
    (EL:DLToken (EL:Get 'device-id entry)) (EL:DLInt (EL:Get 'revision entry))
    (> (EL:Get 'revision entry) 0) (EL:DLNameKey (EL:Get 'block-name entry))
    (listp (EL:Get 'aliases entry)) (equal (type (EL:Get 'display entry)) 'STR)
    (or (not (EL:Get 'watts entry)) (EL:DLInt (EL:Get 'watts entry)))
    (EL:DLBoolField 'zero-confirmed entry) (EL:DLBoolField 'is-ground entry)
    (EL:DLBoolField 'ground-confirmed entry) (EL:DLBoolField 'active entry)
    (member (EL:Get 'status entry) '(ready draft deleted))
    (EL:DLInt (EL:Get 'asset-revision entry))
    (or (not (EL:Get 'active entry)) (equal (EL:Get 'status entry) 'ready))
    (or (not (equal (EL:Get 'status entry) 'ready)) (EL:DLEntryReady entry))))
  (if ok
    (foreach name (EL:DLEntryNames entry)
      (setq key (EL:DLNameKey name))
      (if (or (not key) (member key seen)) (setq ok nil))
      (setq seen (cons key seen)))) ok)
(defun EL:DLCatalogInitial (identity)
  (list '(schema . EL_DEVICE_LIBRARY_V1) (cons 'library-id identity) '(revision . 0) '(next-id . 1) '(devices)))
(defun EL:DLCatalogValid (catalog / good ids names entry name key)
  (setq good (and (EL:OnlyKeys catalog '(schema library-id revision next-id devices))
    (equal (EL:Get 'schema catalog) 'EL_DEVICE_LIBRARY_V1)
    (EL:DLToken (EL:Get 'library-id catalog)) (EL:DLInt (EL:Get 'revision catalog))
    (EL:DLInt (EL:Get 'next-id catalog)) (> (EL:Get 'next-id catalog) 0) (listp (EL:Get 'devices catalog))))
  (if good
    (foreach entry (EL:Get 'devices catalog)
      (if (or (not (EL:DLEntryValid entry)) (member (EL:Get 'device-id entry) ids)) (setq good nil))
      (setq ids (cons (EL:Get 'device-id entry) ids))
      (if (not (equal (EL:Get 'status entry) 'deleted))
        (foreach name (EL:DLEntryNames entry)
          (setq key (EL:DLNameKey name))
          (if (member key names) (setq good nil)) (setq names (cons key names)))))) good)
(defun EL:DLNextID (catalog / serial identity)
  (setq serial (EL:Get 'next-id catalog) identity (strcat "ELDEV" (itoa serial)))
  (while (EL:By 'device-id identity (EL:Get 'devices catalog))
    (setq serial (1+ serial) identity (strcat "ELDEV" (itoa serial)))) identity)
(defun EL:DLEntryNew (catalog name)
  (list (cons 'device-id (EL:DLNextID catalog)) '(revision . 0) (cons 'block-name name) '(aliases)
    (cons 'display name) '(watts) '(zero-confirmed) '(is-ground) '(ground-confirmed)
    '(active) '(status . draft) '(asset-revision . 0) '(block-file) '(legend-file) '(legend-size) '(legend-checksum)))
(defun EL:DLCollisionName (catalog / seen entry name key collision)
  (foreach entry (EL:Get 'devices catalog)
    (if (not (equal (EL:Get 'status entry) 'deleted))
      (foreach name (EL:DLEntryNames entry)
        (setq key (EL:DLNameKey name))
        (if (member key seen) (setq collision name)) (setq seen (cons key seen))))) collision)
(defun EL:DLUpsert (catalog entry / old next rows collision)
  (setq *EL:DLError* nil old (EL:By 'device-id (EL:Get 'device-id entry) (EL:Get 'devices catalog)))
  (cond
    ((not (EL:DLCatalogValid catalog)) (EL:DLFail "设备库结构无效，未写入。"))
    ((not (equal (EL:Get 'revision entry) (if old (EL:Get 'revision old) 0)))
      (EL:DLFail "设备项已被修改，请刷新后重试；当前输入保留。"))
    (T
      (setq entry (EL:Put 'revision (1+ (EL:Get 'revision entry)) entry)
        rows (if old (subst entry old (EL:Get 'devices catalog)) (append (EL:Get 'devices catalog) (list entry)))
        next (EL:Put 'revision (1+ (EL:Get 'revision catalog)) (EL:Put 'devices rows catalog)))
      (if (not old) (setq next (EL:Put 'next-id (1+ (EL:Get 'next-id catalog)) next)))
      (if (EL:DLCatalogValid next) next
        (if (setq collision (EL:DLCollisionName next)) (EL:DLFail (strcat "图块名或别名冲突：" collision "；未写入。"))
          (EL:DLFail "设备资料无效，未写入；请核对功率、地面及图形资料。"))))))
(defun EL:DLDelete (catalog identity / entry)
  (if (setq entry (EL:By 'device-id identity (EL:Get 'devices catalog)))
    (EL:DLUpsert catalog (EL:Put 'active nil (EL:Put 'status 'deleted entry)))
    (EL:DLFail "设备项不存在。")))
(defun EL:DLRestore (catalog identity / entry ready)
  (if (setq entry (EL:By 'device-id identity (EL:Get 'devices catalog)))
    (progn (setq ready (EL:DLEntryReady entry))
      (EL:DLUpsert catalog (EL:Put 'active (if ready T nil) (EL:Put 'status (if ready 'ready 'draft) entry))))
    (EL:DLFail "设备项不存在。")))
(defun EL:DLIndex (catalog / index entry name)
  (foreach entry (EL:Get 'devices catalog)
    (if (and (EL:Get 'active entry) (equal (EL:Get 'status entry) 'ready))
      (foreach name (EL:DLEntryNames entry) (setq index (cons (cons (EL:DLNameKey name) entry) index))))) index)
;; Date: 2026-10-22. Exact names win; a suffix fallback must identify a single device.
(defun EL:DLUniqueNameEntry (name entries / key entry found ambiguous ids)
  (if (setq key (EL:TianzhengNameKey name))
    (foreach entry entries
      (if (member key (mapcar 'EL:BlockNameMatchKey (EL:DLEntryNames entry)))
        (progn
          (setq ids (EL:Unique (cons (EL:Get 'device-id entry) ids)))
          (if (and found (not (equal (EL:Get 'device-id entry) (EL:Get 'device-id found))))
            (setq ambiguous T) (setq found entry))))))
  (if ambiguous
    (progn (EL:LogEvent "DEVICE_NAME_SUFFIX_AMBIGUOUS"
      (list (cons 'drawing-name name) (cons 'match-key key) (cons 'device-ids ids))) nil)
    found))
(defun EL:DLLookup (name snapshot)
  (cond ((cdr (assoc (EL:DLNameKey name) (EL:Get 'index snapshot))))
    ((EL:DLUniqueNameEntry name (mapcar 'cdr (EL:Get 'index snapshot))))))
;; Date: 2026-10-12. Picked drafts have real graphics before default watts are complete.
(defun EL:DLFindEntry (name snapshot / found entry)
  (foreach entry (EL:Get 'devices (EL:Get 'catalog snapshot))
    (if (and (not (equal (EL:Get 'status entry) 'deleted))
      (member (EL:DLNameKey name) (mapcar 'EL:DLNameKey (EL:DLEntryNames entry)))) (setq found entry)))
  (cond (found) ((EL:DLUniqueNameEntry name (vl-remove-if '(lambda (entry)
    (equal (EL:Get 'status entry) 'deleted)) (EL:Get 'devices (EL:Get 'catalog snapshot)))))))
;; Date: 2026-10-13. Registered draft graphics may already have a saved default power.
(defun EL:DLPowerEntry (name snapshot / entry)
  ;; A disabled/draft exact row must not inherit a different author's active power.
  (setq entry (cond ((cdr (assoc (EL:DLNameKey name) (EL:Get 'index snapshot))))
    ((assoc 'catalog snapshot) (EL:DLFindEntry name snapshot)) (T (EL:DLLookup name snapshot))))
  (cond ((and entry (EL:Get 'active entry) (equal (EL:Get 'status entry) 'ready)) entry)
    ((and entry (equal (EL:Get 'status entry) 'draft)
      (EL:DLEntryAssets entry) (EL:DLInt (EL:Get 'watts entry))
      (or (> (EL:Get 'watts entry) 0) (EL:Get 'zero-confirmed entry))) entry)))
(defun EL:DLRecognitionNames (snapshot / names entry)
  (foreach entry (EL:Get 'devices (EL:Get 'catalog snapshot))
    (if (and (EL:DLEntryAssets entry)
      (or (equal (EL:Get 'status entry) 'draft)
        (and (equal (EL:Get 'status entry) 'ready) (EL:Get 'active entry))))
      (setq names (append names (EL:DLEntryNames entry))))) (EL:Unique names))
(defun EL:DLSearch (catalog query deleted / out entry text)
  (setq query (strcase query))
  (foreach entry (EL:Get 'devices catalog)
    (setq text (strcase (strcat (EL:Get 'block-name entry) " " (EL:Get 'display entry))))
    (foreach text (list text (strcase (vl-prin1-to-string (EL:Get 'aliases entry))))
      (if (and (or deleted (not (equal (EL:Get 'status entry) 'deleted)))
          (or (= query "") (vl-string-search query text)) (not (member entry out))) (setq out (cons entry out)))) )
  (reverse out))

;; Native I/O boundaries are deliberately small and injectable in checks.
(defun EL:DLUTF8Valid (bytes / good a b c d need rest)
  (setq good T)
  (while (and bytes good)
    (setq a (car bytes) bytes (cdr bytes) need 0)
    (cond
      ((and (>= a 1) (<= a 127)))
      ((and (>= a 194) (<= a 223)) (setq need 1))
      ((and (>= a 224) (<= a 239)) (setq need 2))
      ((and (>= a 240) (<= a 244)) (setq need 3))
      (T (setq good nil)))
    (setq rest bytes)
    (repeat need
      (if (and rest (>= (car rest) 128) (<= (car rest) 191)) (setq rest (cdr rest)) (setq good nil)))
    (if (and good (> need 0))
      (progn
        (setq b (car bytes))
        (if (or (and (= a 224) (< b 160)) (and (= a 237) (> b 159))
            (and (= a 240) (< b 144)) (and (= a 244) (> b 143))) (setq good nil))
        (setq bytes rest)))) good)
(defun EL:DLReadStream (stream path / bytes)
  ;; Date: 2026-10-12. Supply optional COM slots explicitly for CAD2020.
  (vlax-put-property stream 'Type 1) (vlax-invoke-method stream 'Open nil 0 -1 "" "")
  (vlax-invoke-method stream 'LoadFromFile path)
  ;; Date: 2026-10-12. Preserve the validation message; skip a UTF-8 BOM as bytes.
  (cond
    ((> (vlax-get-property stream 'Size) 8388608) (EL:DLFail "设备库索引过大，未读取。"))
    (T
      (setq bytes (vlax-safearray->list (vlax-variant-value (vlax-invoke-method stream 'Read -1))))
      (if (not (EL:DLUTF8Valid bytes)) (EL:DLFail "设备库不是有效 UTF-8，原文件保留。")
        (progn
          (vlax-put-property stream 'Position 0) (vlax-put-property stream 'Type 2)
          (vlax-put-property stream 'Charset "utf-8")
          (if (equal (list (car bytes) (cadr bytes) (caddr bytes)) '(239 187 191))
            (vlax-put-property stream 'Position 3))
          (vlax-invoke-method stream 'ReadText -1))))))
(defun EL:DLReadText (path / stream outcome)
  (setq stream (vl-catch-all-apply 'vlax-create-object (list "ADODB.Stream")))
  (if (vl-catch-all-error-p stream) (EL:DLFail "无法创建 UTF-8 读取接口，请检查 Windows ADODB.Stream。")
    (progn
      (setq outcome (vl-catch-all-apply 'EL:DLReadStream (list stream path)))
      (vl-catch-all-apply 'vlax-invoke-method (list stream 'Close)) (vlax-release-object stream)
      (if (vl-catch-all-error-p outcome)
        (EL:DLFail (strcat "设备库读取失败：" path "；" (vl-catch-all-error-message outcome))) outcome))))
(defun EL:DLWriteStream (stream path text)
  (vlax-put-property stream 'Type 2) (vlax-put-property stream 'Charset "utf-8")
  (vlax-invoke-method stream 'Open nil 0 -1 "" "") (vlax-invoke-method stream 'WriteText text 0)
  (vlax-invoke-method stream 'SaveToFile path 1) T)
(defun EL:DLWriteText (path text / stream outcome)
  (setq stream (vlax-create-object "ADODB.Stream")
    outcome (vl-catch-all-apply 'EL:DLWriteStream (list stream path text)))
  (vl-catch-all-apply 'vlax-invoke-method (list stream 'Close)) (vlax-release-object stream)
  (if (vl-catch-all-error-p outcome) (EL:DLFail (vl-catch-all-error-message outcome)) outcome))
(defun EL:DLParse (text / parsed)
  (if (equal (type text) 'STR)
    (progn
      (setq parsed (vl-catch-all-apply 'EL:StoreParse (list text)))
      (if (and (not (vl-catch-all-error-p parsed)) (EL:DLCatalogValid parsed)) parsed
        (EL:DLFail "设备库索引损坏或版本不支持，原文件保留。")))))
(defun EL:DLMkdir (path / parent)
  (if (vl-file-directory-p path) T
    (progn (setq parent (vl-filename-directory (vl-string-right-trim "/\\" path)))
      (and parent (not (equal parent path)) (EL:DLMkdir parent) (vl-mkdir path)))))
(defun EL:DLOperationID (/ ticks)
  (setq *EL:DLSerial* (1+ (cond (*EL:DLSerial*) (T 0))))
  (strcat "op-" (EL:Hash (strcat (cond ((getenv "COMPUTERNAME")) (T "CAD"))
    (rtos (getvar "CDATE") 2 8) "-" (itoa (getvar "MILLISECS")) "-" (itoa *EL:DLSerial*)))))
(defun EL:DLDefaultRoot (/ base)
  (if (setq base (getenv "LOCALAPPDATA"))
    (EL:NormalizeRoot (strcat base "/Emergency-Lighting/device-library"))))
(defun EL:DLRoot (/ saved)
  (cond (*EL:DLRoot*)
    ((setq saved (vl-registry-read "HKEY_CURRENT_USER\\Software\\Emergency-Lighting\\DeviceLibrary" "Root"))
      (EL:NormalizeRoot saved)) (T (EL:DLDefaultRoot))))
(defun EL:DLRootSet (root / path)
  (setq path (EL:NormalizeRoot root))
  (if (and path (vl-file-directory-p path)
      (vl-registry-write "HKEY_CURRENT_USER\\Software\\Emergency-Lighting\\DeviceLibrary" "Root" path))
    (progn (setq *EL:DLRoot* path *EL:DLCache* nil) path)
    (EL:DLFail "设备库目录未保存，请检查目录和用户配置权限。")))
(defun EL:DLSnapshotLoad (root / path text catalog)
  (setq *EL:DLError* nil root (EL:NormalizeRoot root) path (strcat root "catalog.eld"))
  (EL:PerfCount "device-library-loads" 1)
  (cond
    ((findfile (strcat root ".write-lock"))
      (EL:LogEvent "DEVICE_LIBRARY_LOCKED" (list (cons 'path (strcat root ".write-lock"))))
      (EL:DLFail "设备库存在写入占用文件，暂时无法打开；当前输入保留。"))
    ((findfile path)
      (if (and (setq text (EL:DLReadText path)) (setq catalog (EL:DLParse text)))
        (list (cons 'root root) (cons 'catalog catalog) (cons 'raw text) (cons 'present T) (cons 'index (EL:DLIndex catalog)))))
    (T (setq catalog (EL:DLCatalogInitial (strcat "LIB-" (EL:DLOperationID))))
      (list (cons 'root root) (cons 'catalog catalog) '(raw) '(present) '(index)))))
(defun EL:DLSnapshotCurrent (snapshot / path raw)
  (setq path (strcat (EL:Get 'root snapshot) "catalog.eld"))
  (and snapshot (not (findfile (strcat (EL:Get 'root snapshot) ".write-lock")))
    (if (EL:Get 'present snapshot)
      (and (findfile path) (setq raw (EL:DLReadText path)) (equal raw (EL:Get 'raw snapshot)))
      (not (findfile path)))))
(defun EL:DLSnapshot (/ root scope loaded)
  (setq scope (if *EL:PerfActive* *EL:StoreReadScope*))
  (if (and scope *EL:DLCache* (equal scope (EL:Get 'scope *EL:DLCache*))) *EL:DLCache*
    (if (setq root (EL:DLRoot))
      (progn (setq loaded (EL:PerfCall "DEVICE_LIBRARY_LOAD" 'EL:DLDefaultSnapshot (list root)))
        (if loaded (setq loaded (EL:Put 'scope scope loaded)))
        (if scope (setq *EL:DLCache* loaded)) loaded)
      (EL:DLFail "无法取得用户设备库目录。"))))
(defun EL:DLLockWork (fso path owner)
  (setq *EL:DLLockStream* (vlax-invoke-method fso 'CreateTextFile path :vlax-false :vlax-false) *EL:DLLockClaimed* T)
  (vlax-invoke-method *EL:DLLockStream* 'WriteLine owner) T)
(defun EL:DLLockAcquire (path owner / fso result closed *EL:DLLockClaimed* *EL:DLLockStream*)
  (setq fso (vlax-create-object "Scripting.FileSystemObject")
    result (vl-catch-all-apply 'EL:DLLockWork (list fso path owner)))
  ;; Close/release even when WriteLine fails; otherwise the marker cannot be removed.
  (if *EL:DLLockStream*
    (progn (setq closed (vl-catch-all-apply 'vlax-invoke-method (list *EL:DLLockStream* 'Close)))
      (vl-catch-all-apply 'vlax-release-object (list *EL:DLLockStream*))))
  (vlax-release-object fso)
  (if (or (vl-catch-all-error-p result) (vl-catch-all-error-p closed))
    (progn (if *EL:DLLockClaimed* (vl-file-delete path)) (EL:DLFail "设备库写锁被占用或目录不可写，请重试。")) result))
;; Date: 2026-10-11. ASCII ownership must not depend on catalog UTF-8/ADODB reads.
(defun EL:DLLockOwner (path / file text)
  (if (setq file (open path "r"))
    (progn (setq text (vl-catch-all-apply 'read-line (list file))) (close file)
      (if (not (vl-catch-all-error-p text)) text))))
(defun EL:DLLockRelease (path owner / text removed)
  (if (not (findfile path)) T
    (progn (setq text (vl-catch-all-apply 'EL:DLLockOwner (list path)))
      (if (and (not (vl-catch-all-error-p text)) (equal text owner))
        (setq removed (vl-file-delete path)))
      (if (not removed) (EL:LogEvent "DEVICE_LIBRARY_LOCK_RELEASE_FAILED" (list (cons 'path path)))) removed)))
;; Date: 2026-10-11. Explicit recovery only after the user confirms all other writers stopped.
;; Archive the marker; never overwrite a catalog or discard unfinished publish evidence.
(defun EL:DLLockRecover (root / path catalog owner backup)
  (setq root (EL:NormalizeRoot root) path (strcat root ".write-lock") catalog (strcat root "catalog.eld")
    *EL:DLError* nil)
  (cond
    ((not (findfile path)) T)
    ((vl-file-directory-p path) (EL:DLFail "占用路径是目录，不能按锁文件恢复；原文件保留。"))
    ((if (findfile catalog) (not (EL:DLParse (EL:DLReadText catalog)))
       (or (vl-directory-files root "rollback-*.eld" 1)
           (and (vl-file-directory-p (strcat root "history")) (vl-directory-files (strcat root "history") "*.eld" 1))
           (and (vl-file-directory-p (strcat root ".staging")) (vl-directory-files (strcat root ".staging") "*.eld" 1))))
      (EL:DLFail "索引缺失或损坏，存在未完成保存的可能；请保留整个库目录，先恢复索引。"))
    ((not (or (= (vl-file-size path) 0)
        (and (setq owner (EL:DLLockOwner path)) (EL:DLToken owner) (= (substr owner 1 3) "op-"))))
      (EL:DLFail "占用文件无法识别或读取，未移动；请保留文件用于检查。"))
    (T
      (setq backup (strcat root "lock-recovered-" (EL:DLOperationID) ".txt"))
      (if (and (not (findfile backup)) (equal owner (EL:DLLockOwner path)) (vl-file-rename path backup))
        (progn (setq *EL:DLCache* nil) (EL:LogEvent "DEVICE_LIBRARY_LOCK_RECOVERED" (list (cons 'backup backup))) T)
        (EL:DLFail "占用文件仍被使用或目录不可写，未恢复；请结束其他 CAD 中的保存后重试。")))))
(defun EL:DLCommitLocked (snapshot candidate / root path text current tmp backup history result)
  (setq root (EL:Get 'root snapshot) path (strcat root "catalog.eld")
    current (if (findfile path) (EL:DLReadText path)))
  (EL:Require (if (EL:Get 'present snapshot) (equal current (EL:Get 'raw snapshot)) (not (findfile path)))
    "设备库已被其他窗口修改，请刷新后重试；当前输入保留。")
  (EL:Require (and (EL:DLCatalogValid candidate)
      (equal (EL:Get 'library-id candidate) (EL:Get 'library-id (EL:Get 'catalog snapshot)))
      (= (EL:Get 'revision candidate) (1+ (EL:Get 'revision (EL:Get 'catalog snapshot))))) "待保存设备库版本无效。")
  (EL:Require (and (EL:DLMkdir (strcat root ".staging")) (EL:DLMkdir (strcat root "history"))) "设备库目录不可写。")
  (setq tmp (vl-filename-mktemp "catalog-" (strcat root ".staging") ".eld")
    backup (vl-filename-mktemp "rollback-" root ".eld") text (vl-prin1-to-string candidate))
  (EL:Require (and (EL:DLWriteText tmp text) (equal (EL:DLParse (EL:DLReadText tmp)) candidate))
    "设备库 UTF-8 写入回读失败，原文件保留。")
  (if current
    (progn
      (setq history (strcat root "history/" (itoa (EL:Get 'revision (EL:Get 'catalog snapshot))) ".eld"))
      (EL:Require (if (findfile history) (equal (EL:DLReadText history) current)
        (and (vl-file-copy path history) (equal (EL:DLReadText history) current))) "历史设备库备份失败。")))
  (if (findfile path) (EL:Require (vl-file-rename path backup) "原设备库无法保留，未替换。"))
  (setq result (vl-catch-all-apply 'vl-file-rename (list tmp path)))
  (if (or (vl-catch-all-error-p result) (not result))
    (progn (if (findfile backup) (vl-file-rename backup path))
      (EL:Require nil "新设备库发布失败，已尝试恢复原索引；请查看目录权限。")))
  (if (not (equal (EL:DLParse (EL:DLReadText path)) candidate))
    (progn (vl-file-delete path) (if (findfile backup) (vl-file-rename backup path))
      (EL:Require nil "已发布设备库回读不一致，已尝试恢复原索引。")))
  (if (findfile backup) (vl-file-delete backup)) T)
(defun EL:DLCommit (snapshot candidate / root lock owner result)
  (setq *EL:DLError* nil root (EL:Get 'root snapshot) lock (strcat root ".write-lock") owner (EL:DLOperationID))
  (if (and snapshot candidate (EL:DLMkdir root) (EL:DLLockAcquire lock owner))
    (progn
      (setq result (vl-catch-all-apply 'EL:DLCommitLocked (list snapshot candidate)))
      (EL:DLLockRelease lock owner)
      (if (vl-catch-all-error-p result) (EL:DLFail (vl-catch-all-error-message result))
        (if result (progn (setq *EL:DLCache* nil) (EL:PerfCount "device-library-writes" 1) T))))))
(princ)
