;; Date: 2026-10-16. Bundled graphics and saved powers seed the user's catalog transactionally.
(defun EL:DLDefaultSource ()
  (if *EL:Root* (strcat (EL:NormalizeRoot *EL:Root*) "assets/default-device-library/")))
(defun EL:DLDefaultMatch (seed catalog / keys entry found)
  ;; Include deleted entries: a user's deletion is never undone by startup.
  (setq keys (mapcar 'EL:DLNameKey (EL:DLEntryNames seed)))
  (foreach entry (EL:Get 'devices catalog)
    (if (and (vl-some '(lambda (name) (member (EL:DLNameKey name) keys)) (EL:DLEntryNames entry))
      (or (not found) (not (equal (EL:Get 'status entry) 'deleted))))
      (setq found entry)))
  ;; Date: 2026-10-22. Existing user values/deletions also cover other computer suffixes.
  (if (not found)
    (progn
      (setq keys (mapcar 'EL:BlockNameMatchKey (EL:DLEntryNames seed)))
      (foreach entry (EL:Get 'devices catalog)
        (if (and (vl-some '(lambda (name) (member (EL:BlockNameMatchKey name) keys)) (EL:DLEntryNames entry))
          (or (not found) (not (equal (EL:Get 'status entry) 'deleted))))
          (setq found entry))))) found)
(defun EL:DLDefaultAssetsPresent (entry snapshot)
  (and (EL:DLEntryAssets entry)
    (findfile (strcat (EL:Get 'root snapshot) (EL:Get 'block-file entry)))
    (findfile (strcat (EL:Get 'root snapshot) (EL:Get 'legend-file entry)))))
;; Date: 2026-10-16. Exact prior records distinguish published defaults from later user edits.
(defun EL:DLDefaultBaselinesRead (source / spec path raw catalog baselines valid key)
  (setq key (list source *EL:PackageMarker*))
  (if (equal key (car *EL:DLDefaultBaselineCache*)) (cdr *EL:DLDefaultBaselineCache*)
    (progn
      (setq valid T)
      (foreach spec '((legacy . "legacy-defaults.eld") (published . "published-power-source.eld"))
        (setq path (strcat source (cdr spec)))
        (if (and (findfile path) (setq raw (EL:DLReadText path))
            (setq catalog (EL:DLParse raw)) (= (length (EL:Get 'devices catalog)) 49))
          (setq baselines (cons (cons (car spec) catalog) baselines))
          (setq valid nil)))
      (if valid
        (progn (setq baselines (reverse baselines) *EL:DLDefaultBaselineCache* (cons key baselines)) baselines)
        (EL:DLFail "自带设备库的升级资料缺失或损坏，当前用户库保留；请重新解压完整包。")))))
(defun EL:DLDefaultPowerUpgrade (seed entry snapshot baselines / item previous updated fields)
  (setq updated entry fields '(block-name aliases display watts zero-confirmed is-ground
    ground-confirmed active status asset-revision legend-size legend-checksum))
  (if (and entry (EL:Get 'active seed) (EL:DLEntryReady seed)
      (not (EL:Get 'active entry)) (not (equal (EL:Get 'status entry) 'deleted))
      (not (and (equal (EL:Get 'root snapshot) (EL:Get 'root (EL:Get 'snapshot *EL:DLUIState*)))
        (EL:Get (EL:Get 'device-id entry) (EL:Get 'drafts *EL:DLUIState*)))))
    (foreach item baselines
      (if (and (or (equal (car item) 'legacy)
            (equal (EL:Get 'library-id (cdr item)) (EL:Get 'library-id (EL:Get 'catalog snapshot))))
          (setq previous (EL:By 'block-name (EL:Get 'block-name entry) (EL:Get 'devices (cdr item))))
          (equal (EL:Get 'revision entry) (EL:Get 'revision previous))
          (equal (mapcar '(lambda (key) (EL:Get key entry)) fields)
            (mapcar '(lambda (key) (EL:Get key previous)) fields)))
        (progn
          (setq updated (EL:Put 'watts (EL:Get 'watts seed)
            (EL:Put 'zero-confirmed (EL:Get 'zero-confirmed seed) entry)))
          (if (EL:DLEntryReady updated)
            (setq updated (EL:Put 'active T (EL:Put 'status 'ready updated)))
            (setq updated entry)))))) updated)
(defun EL:DLDefaultNeeded (defaults snapshot baselines / seed entry needed)
  (foreach seed (EL:Get 'devices defaults)
    (setq entry (EL:DLDefaultMatch seed (EL:Get 'catalog snapshot)))
    (if (or (not entry) (and (not (equal (EL:Get 'status entry) 'deleted))
      (not (EL:DLDefaultAssetsPresent entry snapshot)))
      (not (equal entry (EL:DLDefaultPowerUpgrade seed entry snapshot baselines)))) (setq needed T))) needed)
(defun EL:DLDefaultMerge (defaults source snapshot baselines / catalog seed old entry rows next)
  (setq catalog (EL:Get 'catalog snapshot))
  (foreach seed (EL:Get 'devices defaults)
    (setq old (EL:DLDefaultMatch seed catalog)
      entry (if old (EL:DLDefaultPowerUpgrade seed old snapshot baselines)
        (EL:Put 'device-id (EL:DLNextID catalog) (EL:Put 'revision 0 seed))))
    (if (or (not old) (not (equal entry old)) (and (not (equal (EL:Get 'status old) 'deleted))
      (not (EL:DLDefaultAssetsPresent old snapshot))))
      (progn
        ;; Only exact prior defaults receive published power; other fields stay user-owned.
        (if (not old) (setq entry (EL:Put 'asset-revision 0 entry)))
        (if (or (not old) (not (EL:DLDefaultAssetsPresent old snapshot)))
          (progn
            (setq *EL:DLError* (strcat "复制默认设备“" (EL:Get 'display seed)
              "”的图形未完成，请检查库目录权限和完整交付包。"))
            (setq entry (EL:DLAssetInstall snapshot entry (strcat source (EL:Get 'block-file seed))
              (strcat source (EL:Get 'legend-file seed))) *EL:DLError* nil)))
        (setq entry (EL:Put 'revision (1+ (EL:Get 'revision entry)) entry)
          rows (if old (subst entry old (EL:Get 'devices catalog))
            (append (EL:Get 'devices catalog) (list entry)))
          catalog (EL:Put 'devices rows catalog))
        (if (not old)
          (setq next (1+ (atoi (substr (EL:Get 'device-id entry) 6)))
            catalog (EL:Put 'next-id next catalog))))))
  (EL:Put 'revision (1+ (EL:Get 'revision catalog)) catalog))
(defun EL:DLDefaultInstallLocked (defaults source snapshot baselines / candidate)
  ;; Compare the old index before creating immutable asset revisions.
  (setq *EL:DLError* "设备库已变化，默认设备未写入；请刷新重试。")
  (EL:Require (if (EL:Get 'present snapshot)
      (equal (EL:DLReadText (strcat (EL:Get 'root snapshot) "catalog.eld")) (EL:Get 'raw snapshot))
      (not (findfile (strcat (EL:Get 'root snapshot) "catalog.eld"))))
    "设备库已变化，默认设备未写入；请刷新重试。")
  (setq *EL:DLError* nil candidate (EL:DLDefaultMerge defaults source snapshot baselines)
    *EL:DLError* "默认设备库索引保存和回读未完成，请检查目录权限后重试。")
  (if (EL:DLCommitLocked snapshot candidate) (progn (setq *EL:DLError* nil) T)))
(defun EL:DLDefaultEnsure (snapshot / source defaults baselines root lock owner outcome loaded)
  (setq source (EL:DLDefaultSource) root (EL:Get 'root snapshot))
  (cond
    ((not snapshot) nil)
    ((or (not source) (not (findfile (strcat source "catalog.eld")))) snapshot)
    ((equal (list root source (EL:Get 'raw snapshot)) *EL:DLDefaultCache*) snapshot)
    ((not (setq defaults (EL:DLParse (EL:DLReadText (strcat source "catalog.eld"))))) snapshot)
    ((/= (length (EL:Get 'devices defaults)) 53)
      (EL:DLFail "默认设备库不完整，请重新解压完整应急照明包。") snapshot)
    ((not (setq baselines (EL:DLDefaultBaselinesRead source))) snapshot)
    ((not (EL:DLDefaultNeeded defaults snapshot baselines))
      (setq *EL:DLDefaultCache* (list root source (EL:Get 'raw snapshot))) snapshot)
    (T
      (setq lock (strcat root ".write-lock") owner (EL:DLOperationID))
      (if (and (EL:DLMkdir root) (EL:DLLockAcquire lock owner))
        (progn
          (setq outcome (vl-catch-all-apply 'EL:DLDefaultInstallLocked (list defaults source snapshot baselines)))
          (EL:DLLockRelease lock owner)
          (if (and (not (vl-catch-all-error-p outcome)) outcome
              (setq loaded (EL:DLSnapshotLoad root)))
            (progn
              (setq snapshot loaded *EL:DLCache* nil *EL:DLDefaultCache* (list root source (EL:Get 'raw loaded)))
              (EL:LogEvent "DEFAULT_DEVICE_LIBRARY_INSTALLED" (list (cons 'root root) (cons 'count (length (EL:Get 'devices defaults)))))
              (princ "\n自带设备库默认功率已自动初始化或升级；可在 ELDEVLIB 中直接查看或修改。"))
            (EL:DLFail (strcat "默认设备库安装未完成，原资料保留，请刷新重试："
              (cond (*EL:DLError*) ((vl-catch-all-error-p outcome) (vl-catch-all-error-message outcome))
                (T "复制或索引保存失败。"))))))
        (if (not *EL:DLError*) (EL:DLFail "默认设备库目录不可写，请检查当前用户目录权限。"))) snapshot)))
(defun EL:DLDefaultSnapshot (root / snapshot outcome)
  ;; Every entry point keeps the original library and reports a specific read failure.
  (setq *EL:DLError* nil root (EL:NormalizeRoot root))
  (if (not root) (EL:DLFail "无法取得设备库目录，请检查当前 Windows 用户的本地数据目录。")
  (progn (setq outcome (vl-catch-all-apply 'EL:DLSnapshotLoad (list root)))
  (if (vl-catch-all-error-p outcome)
    (EL:DLFail (strcat "无法读取设备库：" root "；" (vl-catch-all-error-message outcome)))
    (if outcome
      (progn
        (setq snapshot outcome outcome (vl-catch-all-apply 'EL:DLDefaultEnsure (list snapshot)))
        (if (vl-catch-all-error-p outcome)
          (progn (EL:DLFail (strcat "默认设备库未补齐，原资料保留："
            (cond (*EL:DLError*) (T (vl-catch-all-error-message outcome))))) snapshot) outcome)))))))
(defun EL:DLDefaultStartup (/ snapshot)
  (setq *EL:DLDefaultCache* nil)
  (if (and (EL:DLDefaultSource) (findfile (strcat (EL:DLDefaultSource) "catalog.eld")))
    (progn (setq snapshot (EL:DLDefaultSnapshot (EL:DLRoot)))
      (if *EL:DLError* (princ (strcat "\n" *EL:DLError*))) snapshot)
    (progn (EL:DLFail "交付包缺少默认设备库，请保留完整解压目录后重新加载。")
      (princ (strcat "\n" *EL:DLError*)) nil)))
(princ)
