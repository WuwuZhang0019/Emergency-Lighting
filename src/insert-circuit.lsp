;; Date: 2026-10-21. Drawing definitions are the default; library import is explicit.
(defun EL:SystemBlockSource ()
  (if (equal *EL:SystemBlockSource* 'library) 'library 'drawing))
(defun EL:SystemMissingText (blocks styles / text name)
  (setq text "")
  (foreach name blocks (setq text (strcat text "\n图块：" name)))
  (foreach name styles (setq text (strcat text "\n文字样式：" name))) text)
(defun EL:SystemBlockNotice (message)
  (setq *EL:SystemBlockNotice* message) (princ (strcat "\n" message)) nil)
(defun EL:SystemBlockLibraryPath (/ path)
  (cond
    ((and (equal (type *EL:Root*) 'STR) (/= *EL:Root* ""))
      (strcat (vl-string-right-trim "/\\" *EL:Root*) "/templates/系统图块库.dwg"))
    ((setq path (findfile "CCKK.lsp"))
      (strcat (vl-filename-directory path) "/templates/系统图块库.dwg"))
    ((findfile "系统图块库.dwg"))))
(defun EL:SystemMissingSymbols (kind names / name missing)
  (foreach name names (if (not (tblsearch kind name)) (setq missing (cons name missing))))
  (reverse missing))
(defun EL:SystemSourceObjects (database kind names / table name objects object)
  (setq table (if (equal kind "BLOCK") (vla-get-Blocks database) (vla-get-TextStyles database)))
  (foreach name names
    (setq object (vl-catch-all-apply 'vla-Item (list table name)))
    (if (vl-catch-all-error-p object)
      (setq *EL:SystemBlockNotice* (strcat (if *EL:SystemBlockNotice* *EL:SystemBlockNotice* "")
        "\n系统图库无法读取" (if (equal kind "BLOCK") "图块：" "文字样式：") name
        "（" (vl-catch-all-error-message object) "）"))
      (setq objects (cons object objects))))
  (reverse objects))
(defun EL:SystemCopySymbols (database target kind objects / array index object)
  (if objects
    (progn
      (setq array (vlax-make-safearray vlax-vbObject (cons 0 (1- (length objects)))) index 0)
      (foreach object objects
        (vlax-safearray-put-element array index object) (setq index (1+ index)))
      (EL:FreshBoundary)
      (vla-CopyObjects database array
        (if (equal kind "BLOCK") (vla-get-Blocks target) (vla-get-TextStyles target)))
      (EL:FreshBoundary))))
(defun EL:SystemImportWork (path blocks styles / application target block-objects style-objects)
  (setq application (vlax-get-acad-object) target (vla-get-ActiveDocument application)
    *EL:SystemLibraryDBX* (vla-GetInterfaceObject application
      (strcat "ObjectDBX.AxDbDocument." (itoa (atoi (getvar "ACADVER"))))))
  (EL:PerfCall "SYSTEM_LIBRARY_OPEN" 'vlax-invoke-method (list *EL:SystemLibraryDBX* 'Open path))
  ;; Recheck after opening the library; never replace definitions already present.
  (setq blocks (EL:SystemMissingSymbols "BLOCK" blocks) styles (EL:SystemMissingSymbols "STYLE" styles))
  ;; Complete both source-table lookups before any target-table write.
  (setq block-objects (EL:SystemSourceObjects *EL:SystemLibraryDBX* "BLOCK" blocks)
    style-objects (EL:SystemSourceObjects *EL:SystemLibraryDBX* "STYLE" styles))
  (if (not *EL:SystemBlockNotice*)
    (progn
      (EL:PerfCall "SYSTEM_BLOCK_COPY" 'EL:SystemCopySymbols
        (list *EL:SystemLibraryDBX* target "BLOCK" block-objects))
      ;; A cloned block may already have brought in a requested text style.
      (setq style-objects (EL:SystemSourceObjects *EL:SystemLibraryDBX* "STYLE"
        (EL:SystemMissingSymbols "STYLE" styles)))
      (if (not *EL:SystemBlockNotice*)
        (EL:PerfCall "SYSTEM_STYLE_COPY" 'EL:SystemCopySymbols
          (list *EL:SystemLibraryDBX* target "STYLE" style-objects)))
      (and (not *EL:SystemBlockNotice*) (not (EL:SystemMissingSymbols "BLOCK" blocks))
        (not (EL:SystemMissingSymbols "STYLE" styles))))))
(defun EL:EnsureSystemBlocks (blocks styles / missing-blocks missing-styles path result pending *EL:SystemLibraryDBX*)
  (setq *EL:SystemBlockNotice* nil missing-blocks (EL:SystemMissingSymbols "BLOCK" blocks)
    missing-styles (EL:SystemMissingSymbols "STYLE" styles))
  (cond
    ((not (or missing-blocks missing-styles)) T)
    ((not (equal (EL:SystemBlockSource) 'library))
      (EL:SystemBlockNotice (strcat "当前图纸缺少系统图定义："
        (EL:SystemMissingText missing-blocks missing-styles)
        "\n请选择从图库补入缺少图块并准备模板；当前输入保留。")))
    ((not (and (setq path (EL:SystemBlockLibraryPath)) (findfile path)))
      (EL:SystemBlockNotice (strcat "缺少 templates/系统图块库.dwg，请重新解压完整交付包。"
        (EL:SystemMissingText missing-blocks missing-styles) "\n当前输入保留。")))
    (T
      (vl-load-com)
      (princ "\n正在从系统图块库.dwg 导入缺少的系统图块和文字样式。")
      (setq pending *EL:PerfPending*)
      (EL:FreshBoundary)
      (setq result (vl-catch-all-apply 'EL:SystemImportWork (list path missing-blocks missing-styles)))
      (if *EL:SystemLibraryDBX* (vl-catch-all-apply 'vlax-release-object (list *EL:SystemLibraryDBX*)))
      (EL:FreshBoundary)
      (EL:PerfUnwind pending)
      (cond
        ((vl-catch-all-error-p result)
          (EL:SystemBlockNotice (strcat "系统图块库导入失败：" (vl-catch-all-error-message result)
            (EL:SystemMissingText (EL:SystemMissingSymbols "BLOCK" blocks)
              (EL:SystemMissingSymbols "STYLE" styles)) "\n当前输入保留。")))
        ((not result)
          (EL:SystemBlockNotice (strcat (if *EL:SystemBlockNotice* *EL:SystemBlockNotice*
            "系统图块库导入后未读到全部所需定义，已停止生成。")
            (EL:SystemMissingText (EL:SystemMissingSymbols "BLOCK" blocks)
              (EL:SystemMissingSymbols "STYLE" styles)) "\n当前输入保留。")))
        (T (setq *EL:SystemBlockNotice* nil)
          (princ "\n所需系统图块和文字样式已导入，继续检查模板。") T)))))
;; Date: 2026-10-09. Standalone circuit/panel insertion with centered labels.
(defun EL:CCKKLayer (name / row)
  (if (not (tblsearch "LAYER" name))
    (entmake (list '(0 . "LAYER") '(100 . "AcDbSymbolTableRecord")
      '(100 . "AcDbLayerTableRecord") (cons 2 name) '(70 . 0) '(62 . 7) '(6 . "Continuous"))))
  (setq row (tblsearch "LAYER" name))
  (if (and row (= 0 (logand (cdr (assoc 70 row)) 5)) (> (cdr (assoc 62 row)) 0)) T
    (progn (princ (strcat "\n请先打开、解冻并解锁图层：" name)) nil)))
(defun EL:CCKKPoint (block dx dy / data base angle)
  (setq data (entget block) base (cdr (assoc 10 data)) angle (cdr (assoc 50 data))
    dx (* dx (cdr (assoc 41 data))) dy (* dy (cdr (assoc 42 data))))
  (list (+ (car base) (- (* dx (cos angle)) (* dy (sin angle))))
    (+ (cadr base) (+ (* dx (sin angle)) (* dy (cos angle)))) (caddr base)))
(defun EL:CCKKText (block label dx dy layer style color / data angle point normal)
  (setq data (entget block) angle (cdr (assoc 50 data)) normal (cdr (assoc 210 data))
    point (EL:CCKKPoint block dx dy))
  (if (not normal) (setq normal '(0.0 0.0 1.0)))
  (if (entmake (list '(0 . "TEXT") '(100 . "AcDbEntity") (cons 8 layer)
      (cons 62 color) '(6 . "ByLayer") '(48 . 1.0) '(370 . -1) '(440 . 0)
      '(100 . "AcDbText") (cons 10 point) '(40 . 350.0) (cons 1 label)
      (cons 50 angle) '(41 . 0.7) '(51 . 0.0) (cons 7 style)
      '(71 . 0) '(72 . 1) (cons 11 point) (cons 210 normal) '(39 . 0.0)
      '(100 . "AcDbText") '(73 . 0)))
    (entlast)))
(defun EL:CCKKInsert (blockname style textlayer color labels commandname / *error* saved item before block created text)
  (defun *error* (message)
    (foreach item created (if (entget item) (entdel item)))
    (foreach item saved (setvar (car item) (cdr item)))
    (if (and message (not (wcmatch (strcase message) "*CANCEL*,*QUIT*,*EXIT*,*BREAK*")))
      (princ (strcat "\n" commandname " 插入失败：" message))
      (princ "\n已取消插入。"))
    (princ))
  (cond
    ((not (EL:EnsureSystemBlocks (list blockname) (list style))) nil)
    ((not (tblsearch "BLOCK" blockname))
      (princ (strcat "\n当前图纸没有图块 " blockname "，请先将该图块复制到本图。")))
    ((not (tblsearch "STYLE" style))
      (princ (strcat "\n当前图纸没有文字样式 " style "，请先复制使用该样式的文字到本图。")))
    ((and (EL:CCKKLayer "SYS_系统标注_E") (EL:CCKKLayer textlayer))
      (foreach item '("CMDECHO" "ATTREQ" "DRAGMODE" "CLAYER")
        (setq saved (cons (cons item (getvar item)) saved)))
      (setvar "CMDECHO" 0)
      (setvar "ATTREQ" 0)
      (setvar "DRAGMODE" 2)
      (setvar "CLAYER" "SYS_系统标注_E")
      (setq before (entlast))
      (princ "\n移动鼠标预览图块，左键点击插入并添加文字，Esc 取消。")
      (command "_.-INSERT" blockname "_Scale" 1.0 "_Rotate" 0.0 pause)
      (setq block (entlast))
      (if (and block (not (equal block before)) (equal (cdr (assoc 0 (entget block))) "INSERT"))
        (progn
          (setq created (list block))
          (foreach item labels
            (setq text (EL:CCKKText block (car item) (cadr item) (caddr item) textlayer style color))
            (if text (setq created (cons text created))
              (progn (princ "\n文字创建失败，本次图块和文字将清理。") (exit))))))
      (foreach item saved (setvar (car item) (cdr item)))))
  (princ))
(defun c:CCKK ()
  (EL:CCKKInsert "ZYF_Tool_应急照明配电回路图块" "_TEL_DIM" "TEL_TEXT" 256
    '(("疏散指示及应急照明" 10983.0 65.0) ("132W" 10983.0 -450.0)) "CCKK"))
(defun c:CCKK1 ()
  (EL:CCKKInsert "ZYF_Tool_应急照明配电箱图块" "ICDA-STYLE1" "SYS_系统标注_E" 0
    '(("CK-B1AL1" 2450.0 -455.0)) "CCKK1"))
;; Date: 2026-10-09. Standalone assembly; no statistics or DWG draft store.
(defun EL:CCKK2Rows (count / index total rows)
  (if (and (equal (type count) 'INT) (<= 1 count) (<= count 8))
    (progn
      (setq total (+ count (cond ((<= count 6) 2) ((= count 7) 1) (T 0))) index 0)
      (repeat total
        (setq rows (cons (list 6427.0 (- -5500.0 (* 1200.0 index))
          (if (< index count) "普通" "预留")) rows) index (1+ index)))
      (reverse rows))))
(defun EL:CCKK2Require (condition message)
  (if (not condition) (progn (princ (strcat "\n" message)) (exit))) condition)
(defun EL:CCKKValue (value)
  (cond
    ((equal (type value) 'VARIANT) (EL:CCKKValue (vlax-variant-value value)))
    ((equal (type value) 'SAFEARRAY) (EL:CCKKValue (vlax-safearray->list value)))
    ((listp value) (mapcar 'EL:CCKKValue value))
    (T value)))
(defun EL:CCKKVisibility (entity state / object property matches values old)
  (setq object (vlax-ename->vla-object entity))
  (EL:CCKK2Require (= (vla-get-IsDynamicBlock object) :vlax-true) "回路图块不是可用的动态图块。")
  (foreach property (vlax-invoke object 'GetDynamicBlockProperties)
    (if (equal (vla-get-PropertyName property) "可见性1") (setq matches (cons property matches))))
  (EL:CCKK2Require (= (length matches) 1) "回路图块必须具有唯一的可见性1属性。")
  (setq property (car matches) values (EL:CCKKValue (vlax-get-property property 'AllowedValues)))
  (EL:CCKK2Require (and (= (vla-get-ReadOnly property) :vlax-false) (member state values))
    (strcat "可见性1不可写或不支持状态：" state))
  (setq old (vla-get-Value property))
  (vla-put-Value property (vlax-make-variant state (vlax-variant-type old)))
  (EL:CCKK2Require (equal state (EL:CCKKValue (vla-get-Value property)))
    (strcat "可见性1写入后回读不一致：" state)) T)
(defun EL:CCKK2Track (entity)
  (EL:CCKK2Require entity "图块或文字创建失败。")
  (setq *EL:CCKK2Created* (cons entity *EL:CCKK2Created*)) entity)
(defun EL:CCKK2Insert (name point / before entity)
  (setq before (entlast))
  (if point
    (command "_.-INSERT" name "_Scale" 1.0 "_Rotate" 0.0 "_non" point)
    (command "_.-INSERT" name "_Scale" 1.0 "_Rotate" 0.0 pause))
  (setq entity (entlast))
  (EL:CCKK2Require (and entity (not (equal entity before))
    (equal (cdr (assoc 0 (entget entity))) "INSERT")) "未插入新图块。")
  (EL:CCKK2Track entity))
(defun EL:CCKK2Build (panel rows / row circuit point normal origin index)
  (setq index 0)
  (EL:CCKK2Track (EL:CCKKCaptionText panel 'panel))
  (setq normal (cdr (assoc 210 (entget panel))))
  (if (not normal) (setq normal '(0.0 0.0 1.0)))
  (foreach row rows
    (setq point (EL:CCKKPoint panel (car row) (cadr row))
      circuit (EL:CCKK2Insert "ZYF_Tool_应急照明配电回路图块" (trans point normal 1))
      origin (cdr (assoc 10 (entget circuit))))
    (EL:CCKKVisibility circuit (caddr row))
    (setq index (1+ index))
    (EL:CCKK2Track (EL:CCKKText circuit (strcat "ZE" (itoa index)) 2100.0 140.0 "TEL_TEXT" "_TEL_DIM" 256))
    (EL:CCKK2Require (equal origin (cdr (assoc 10 (entget circuit))) 1.0e-6)
      "切换可见性后回路基点发生变化。")
    ;; Reserve labels are already part of the dynamic block.
    (if (not (equal (caddr row) "预留"))
      (progn
        (EL:CCKK2Track (EL:CCKKCaptionText circuit 'purpose))
        (EL:CCKK2Track (EL:CCKKText circuit "132W" 10983.0 -450.0 "TEL_TEXT" "_TEL_DIM" 256))))) T)
;; Date: 2026-10-09. One caption definition for standalone and panel generation.
(defun EL:CCKKCaptionDef (kind)
  (cond ((equal kind 'panel) '("CK-B1AL1" 2450.0 -455.0 "SYS_系统标注_E" "ICDA-STYLE1" 0))
    ((equal kind 'number) '("ZE1" 2100.0 140.0 "TEL_TEXT" "_TEL_DIM" 256))
    (T '("疏散指示及应急照明" 10983.0 65.0 "TEL_TEXT" "_TEL_DIM" 256))))
(defun EL:CCKKCaptionText (block kind)
  (apply 'EL:CCKKText (cons block (EL:CCKKCaptionDef kind))))
(defun EL:CCKK2Cleanup (/ entity result good)
  (setq good T)
  (foreach entity *EL:CCKK2Created*
    (if (entget entity)
      (progn
        (setq result (vl-catch-all-apply 'entdel (list entity)))
        (if (or (vl-catch-all-error-p result) (not result)) (setq good nil))))) good)
(defun EL:CCKK2Standalone (/ *error* *EL:CCKK2Created* saved item count rows panel cleanup)
  (defun *error* (message)
    (setq cleanup (EL:CCKK2Cleanup))
    (foreach item saved (vl-catch-all-apply 'setvar (list (car item) (cdr item))))
    (if (and message (not (wcmatch (strcase message) "*CANCEL*,*QUIT*,*EXIT*,*BREAK*")))
      (princ (strcat "\nCCKK2 失败：" message)))
    (if cleanup (princ "\nCCKK2 已取消或中止，本次新增图形已清理。")
      (princ "\n本次部分新增图形未能清理，请核对图纸。")) (princ))
  (vl-load-com)
  (EL:CCKK2Require (EL:EnsureSystemBlocks
    '("ZYF_Tool_应急照明配电箱图块" "ZYF_Tool_应急照明配电回路图块") '("_TEL_DIM" "ICDA-STYLE1"))
    "系统图块库自动导入未完成。")
  (foreach item '("ZYF_Tool_应急照明配电回路图块" "ZYF_Tool_应急照明配电箱图块")
    (EL:CCKK2Require (tblsearch "BLOCK" item) (strcat "当前图纸缺少图块：" item)))
  (foreach item '("_TEL_DIM" "ICDA-STYLE1")
    (EL:CCKK2Require (tblsearch "STYLE" item) (strcat "当前图纸缺少文字样式：" item)))
  (EL:CCKK2Require (and (EL:CCKKLayer "SYS_系统标注_E") (EL:CCKKLayer "TEL_TEXT")) "目标图层不可用。")
  (while (not rows)
    (initget 6)
    (setq count (getint "\n输入实际回路数（1-8）<1>："))
    (if (not count) (setq count 1))
    (setq rows (EL:CCKK2Rows count))
    (if (not rows) (princ "\n实际回路数只能为 1 到 8。")))
  (foreach item '("CMDECHO" "ATTREQ" "DRAGMODE" "CLAYER")
    (setq saved (cons (cons item (getvar item)) saved)))
  (setvar "CMDECHO" 0) (setvar "ATTREQ" 0) (setvar "DRAGMODE" 2)
  (setvar "CLAYER" "SYS_系统标注_E")
  (princ "\n移动鼠标放置配电箱，左键点击后生成整组回路和文字，Esc 取消。")
  (setq panel (EL:CCKK2Insert "ZYF_Tool_应急照明配电箱图块" nil))
  (EL:CCKK2Build panel rows)
  (foreach item saved (setvar (car item) (cdr item)))
  (princ (strcat "\n已插入配电箱、" (itoa count) " 条实际回路和 "
    (itoa (- (length rows) count)) " 条预留回路。")) (princ))
;; Date: 2026-10-09. Panel invocation supplies statistics; manual invocation
;; keeps the standalone sample workflow and needs no other loaded modules.
(defun c:CCKK2 ()
  (if *EL:CCKK2Request*
    (EL:CCKK2FromPanel *EL:CCKK2Request*)
    (EL:CCKK2Standalone)))
(princ)
