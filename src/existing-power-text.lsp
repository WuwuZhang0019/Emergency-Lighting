;; Date: 2026-10-13. Read and update explicitly selected existing power text.
;; Instance attributes are supported; block definitions are never write targets.
(defun EL:PowerTextDXF (code data / row depth found value)
  ;; A reactor's 330 inside a 102 group is not the entity's owning record.
  (setq depth 0)
  (foreach row data
    (if (equal (car row) 102)
      (progn
        (setq value (cdr row))
        (cond ((and (equal (type value) 'STR) (equal (substr value 1 1) "{")) (setq depth (1+ depth)))
          ((equal value "}") (setq depth (max 0 (1- depth))))))
      (if (and (= depth 0) (equal (car row) code) (not found)) (setq found row)))) found)
(defun EL:PowerTextModelOwnerP (data / owner)
  (setq owner (cdr (EL:PowerTextDXF 330 data)) owner (if owner (entget owner)))
  (and (equal (cdr (assoc 410 data)) "Model") (not (equal (cdr (assoc 67 data)) 1))
    (equal (cdr (assoc 0 owner)) "BLOCK_RECORD")
    (equal (strcase (cond ((cdr (assoc 2 owner))) (T ""))) "*MODEL_SPACE")))
(defun EL:PowerTextVisibleP (data / layer)
  (setq layer (tblsearch "LAYER" (cdr (assoc 8 data))))
  (and layer (not (equal (cdr (assoc 60 data)) 1))
    (= 0 (logand 5 (cond ((cdr (assoc 70 layer))) (T 0))))
    (> (cond ((cdr (assoc 62 layer))) (T 7)) 0)))
(defun EL:PowerTextLocalInsertP (entity / data name definition)
  (setq data (if entity (entget entity)) name (cdr (assoc 2 data))
    definition (if (equal (type name) 'STR) (tblsearch "BLOCK" name)))
  (and (equal (cdr (assoc 0 data)) "INSERT") (EL:PowerTextModelOwnerP data)
    (EL:PowerTextVisibleP data) definition (not (vl-string-search "|" name))
    (= 0 (logand 28 (cond ((cdr (assoc 70 definition))) (T 0))))))
(defun EL:PowerTextRaw (data / row text parts seen good typ)
  (setq typ (cdr (assoc 0 data)) good T)
  (foreach row data
    (cond
      ((equal (car row) 3)
        (if (or seen (not (equal typ "MTEXT")) (not (equal (type (cdr row)) 'STR)))
          (setq good nil) (setq parts (cons (cdr row) parts))))
      ((equal (car row) 1)
        (if (or seen (not (equal (type (cdr row)) 'STR))) (setq good nil)
          (setq seen T text (cdr row))))))
  (if (and good seen)
    (progn (foreach row parts (setq text (strcat row text))) text)))
(defun EL:PowerTextDisplay (text mtext / index size char next finish depth visible positions good)
  ;; Positions map each visible byte/character to its original raw index.
  ;; Unsupported stacked, Unicode-escaped, field and unknown controls fail closed.
  (setq index 1 size (strlen text) depth 0 visible "" good T)
  (if (or (vl-string-search "%<" text) (vl-string-search ">%" text)) (setq good nil))
  (while (and good (<= index size))
    (setq char (substr text index 1))
    (cond
      ((and mtext (equal char "{")) (setq depth (1+ depth) index (1+ index)))
      ((and mtext (equal char "}"))
        (setq depth (1- depth) good (>= depth 0) index (1+ index)))
      ((and mtext (equal char "\\"))
        (setq next (substr text (1+ index) 1))
        (cond
          ((member next '("L" "l" "O" "o" "K" "k")) (setq index (+ index 2)))
          ((member next '("\\" "{" "}" "~" "P"))
            (setq visible (strcat visible (cond ((equal next "P") "\n") ((equal next "~") " ") (T next)))
              positions (cons index positions) index (+ index 2)))
          ((member next '("A" "C" "c" "F" "f" "H" "Q" "T" "W" "p"))
            (setq finish (vl-string-search ";" text (1+ index)))
            (if finish (setq index (+ finish 2)) (setq good nil)))
          (T (setq good nil))))
      ((or (< (ascii char) 32) (= (ascii char) 127))
        (if (member char '("\n" "\r" "\t"))
          (setq visible (strcat visible char) positions (cons index positions) index (1+ index))
          (setq good nil)))
      (T (setq visible (strcat visible char) positions (cons index positions) index (1+ index)))))
  (if (and good (= depth 0)) (list (cons 'visible visible) (cons 'positions (reverse positions)))))
(defun EL:PowerTextReadBody (entity / data typ raw shown parent parent-data owner point angle direction height extension)
  (setq data (entget entity '("*")) typ (cdr (assoc 0 data)))
  (if (and (member typ '("TEXT" "MTEXT" "ATTRIB")) (EL:PowerTextVisibleP data)
      (or (not (equal typ "ATTRIB"))
        (and (not (assoc 101 data)) (not (member '(100 . "AcDbMText") data))))
      (if (equal typ "ATTRIB")
        (and (= 0 (logand 1 (cond ((cdr (assoc 70 data))) (T 0))))
          (setq parent (cdr (EL:PowerTextDXF 330 data))) (EL:PowerTextLocalInsertP parent))
        (EL:PowerTextModelOwnerP data))
      (setq raw (EL:PowerTextRaw data))
      (not (and (setq extension (cdr (assoc 360 data))) (dictsearch extension "ACAD_FIELD")))
      (setq shown (EL:PowerTextDisplay raw (equal typ "MTEXT"))))
    (progn
      (setq parent-data (if parent (entget parent '("*"))) owner (cdr (assoc 5 parent-data))
        height (cdr (assoc 40 data)) angle (cond ((cdr (assoc 50 data))) (T 0.0)))
      (if (equal typ "MTEXT")
        (setq point (cdr (assoc 10 data)) direction (cdr (assoc 11 data)))
        (progn
          (setq point (if (or (/= (cond ((cdr (assoc 72 data))) (T 0)) 0)
              (/= (cond ((cdr (assoc (if (equal typ "ATTRIB") 74 73) data))) (T 0)) 0))
            (cdr (assoc 11 data)) (cdr (assoc 10 data))))
          (if point (setq point (trans point entity 0)))
          (setq direction (trans (list (cos angle) (sin angle) 0.0) entity 0 T))))
      (if direction (setq angle (atan (cadr direction) (car direction))))
      (if (and point (numberp height) (> height 0.0))
        (append (list (cons 'handle (cdr (assoc 5 data))) (cons 'data data) (cons 'type typ)
          (cons 'text raw) (cons 'point point) (cons 'angle angle) (cons 'height height)
          (cons 'owner owner) (cons 'parent-data parent-data) (cons 'drawing-owner (namedobjdict))) shown)))))
(defun EL:PowerTextRead (entity / outcome)
  (setq outcome (vl-catch-all-apply 'EL:PowerTextReadBody (list entity)))
  (if (not (vl-catch-all-error-p outcome)) outcome))
(defun EL:PowerTextCollect (selection / entities entity ref refs seen index child data done)
  (if (listp selection) (setq entities selection)
    (if selection
      (progn (setq index 0)
        (repeat (sslength selection) (setq entities (cons (ssname selection index) entities) index (1+ index)))
        (setq entities (reverse entities)))))
  (foreach entity entities
    (if (setq ref (EL:PowerTextRead entity))
      (if (not (member (EL:Get 'handle ref) seen))
        (setq refs (cons ref refs) seen (cons (EL:Get 'handle ref) seen))))
    (if (and (EL:PowerTextLocalInsertP entity) (equal (cdr (assoc 66 (entget entity))) 1))
      (progn
        (setq child (entnext entity) done nil)
        (while (and child (not done))
          (setq data (entget child))
          (if (and (equal (cdr (assoc 0 data)) "ATTRIB")
              (equal (cdr (EL:PowerTextDXF 330 data)) entity))
            (progn
              (if (and (setq ref (EL:PowerTextRead child)) (not (member (EL:Get 'handle ref) seen)))
                (setq refs (cons ref refs) seen (cons (EL:Get 'handle ref) seen)))
              (setq child (entnext child)))
            (setq done T)))))) (reverse refs))
(defun EL:PowerTextDigitP (char)
  (and (equal (type char) 'STR) (= (strlen char) 1) (<= 48 (ascii char)) (<= (ascii char) 57)))
(defun EL:PowerTextWordP (char / code)
  (and (equal (type char) 'STR) (= (strlen char) 1) (setq code (ascii (strcase char)))
    (or (and (<= 48 code) (<= code 57)) (and (<= 65 code) (<= code 90))
      (member char '("_" "." "," "+" "-")))))
(defun EL:PowerTextNumberEnd (text start / index size digits dots char)
  (setq index start size (strlen text) digits 0 dots 0)
  (if (member (substr text index 1) '("+" "-")) (setq index (1+ index)))
  (while (and (<= index size) (or (EL:PowerTextDigitP (setq char (substr text index 1))) (equal char ".")))
    (if (equal char ".") (setq dots (1+ dots)) (setq digits (1+ digits)))
    (setq index (1+ index)))
  (if (and (> digits 0) (<= dots 1)) index))
(defun EL:PowerTextToken (ref allowbare / text raw positions index size end unit-start unit-end suffix unit start raw-start raw-end tokens char)
  (setq text (EL:Get 'visible ref) raw (EL:Get 'text ref) positions (EL:Get 'positions ref)
    index 1 size (strlen text))
  (while (<= index size)
    (setq char (substr text index 1))
    (if (and (or (EL:PowerTextDigitP char) (member char '("." "+" "-")))
        (or (= index 1) (not (EL:PowerTextWordP (substr text (1- index) 1))))
        (setq end (EL:PowerTextNumberEnd text index)))
      (progn
        (setq unit-start end)
        (while (and (<= unit-start size) (member (substr text unit-start 1) '(" " "\t")))
          (setq unit-start (1+ unit-start)))
        (setq unit (cond ((equal (strcase (substr text unit-start 2)) "KW") 'kw)
          ((equal (strcase (substr text unit-start 1)) "W") 'w))
          unit-end (+ unit-start (if (equal unit 'kw) 2 1)) suffix unit-end)
        (while (and (<= suffix size) (member (substr text suffix 1) '(" " "\t")))
          (setq suffix (1+ suffix)))
        (if (and unit (or (> unit-end size)
            (not (EL:PowerTextWordP (substr text unit-end 1))))
            (not (equal (substr text suffix 1) "/")))
          (setq tokens (cons (list index end unit) tokens)))
        (setq index end))
      (setq index (1+ index))))
  (if (and (not tokens) allowbare)
    (progn
      (setq start 1)
      (while (and (<= start size) (member (substr text start 1) '(" " "\t" "\r" "\n"))) (setq start (1+ start)))
      (if (and (setq end (EL:PowerTextNumberEnd text start))
          (equal (vl-string-trim " \t\r\n" (substr text end)) ""))
        (setq tokens (list (list start end 'w))))))
  (if (= (length tokens) 1)
    (progn
      (setq start (caar tokens) end (cadr (car tokens)) unit (caddr (car tokens))
        raw-start (nth (1- start) positions) raw-end (1+ (nth (- end 2) positions)))
      ;; Do not move formatting controls embedded between digits.
      (if (equal (substr raw raw-start (- raw-end raw-start)) (substr text start (- end start)))
        (list (cons 'start raw-start) (cons 'end raw-end) (cons 'unit unit))))))
(defun EL:PowerTextWattsString (watts unit / whole remainder text)
  ;; Statistics are integral watts. Avoid RTOS, whose output depends on DIMZIN.
  (if (and (numberp watts) (<= 0 watts) (<= watts 2147483647) (= watts (fix watts)))
    (if (not (equal unit 'kw)) (itoa (fix watts))
      (progn
        (setq whole (fix (/ watts 1000.0)) remainder (- (fix watts) (* whole 1000)) text (itoa whole))
        (if (> remainder 0)
          (setq text (strcat text "." (vl-string-right-trim "0"
            (strcat (cond ((< remainder 10) "00") ((< remainder 100) "0") (T "")) (itoa remainder)))))) text))))
(defun EL:PowerTextChunks (text / codes chunk size result code unicode)
  (setq codes (vl-string->list text) unicode (vl-catch-all-apply 'getvar (list "LISPSYS")))
  (setq unicode (and (numberp unicode) (> unicode 0)))
  (while codes
    (setq chunk nil size 0)
    (while (and codes (< size 250)
        (not (and (= size 249) (not unicode) (<= 128 (car codes)) (<= (car codes) 255) (cdr codes))))
      (setq code (car codes) codes (cdr codes) chunk (cons code chunk) size (1+ size))
      (if (and (not unicode) (<= 128 code) (<= code 255) codes)
        (setq chunk (cons (car codes) chunk) codes (cdr codes) size (1+ size))))
    (setq result (cons (vl-list->string (reverse chunk)) result)))
  (if result (reverse result) (list "")))
(defun EL:PowerTextData (data text / pieces pairs piece row result inserted)
  (if (equal (cdr (assoc 0 data)) "MTEXT")
    (progn
      (setq pieces (EL:PowerTextChunks text))
      (while (cdr pieces) (setq pairs (cons (cons 3 (car pieces)) pairs) pieces (cdr pieces)))
      (setq pairs (reverse (cons (cons 1 (car pieces)) pairs))))
    (setq pairs (list (cons 1 text))))
  (foreach row data
    (if (member (car row) '(1 3))
      (if (not inserted)
        (progn (foreach piece pairs (setq result (cons piece result))) (setq inserted T)))
      (setq result (cons row result))))
  (if inserted (reverse result)))
(defun EL:PowerTextReplacement (ref watts allowbare / token number raw text)
  (if (and ref (setq token (EL:PowerTextToken ref allowbare))
      (setq number (EL:PowerTextWattsString watts (EL:Get 'unit token))))
    (progn
      (setq raw (EL:Get 'text ref)
        text (strcat (substr raw 1 (1- (EL:Get 'start token))) number (substr raw (EL:Get 'end token))))
      (if (equal text raw) (EL:Get 'data ref) (EL:PowerTextData (EL:Get 'data ref) text)))))
(defun EL:PowerTextNonContent (data derived / typ aligned)
  (setq typ (cdr (assoc 0 data)) aligned (and (not (equal typ "MTEXT"))
    (or (/= (cond ((cdr (assoc 72 data))) (T 0)) 0)
      (/= (cond ((cdr (assoc (if (equal typ "ATTRIB") 74 73) data))) (T 0)) 0))))
  (vl-remove-if '(lambda (row) (or (member (car row) '(1 3))
    (and derived (if (equal typ "MTEXT") (member (car row) '(42 43))
      (and aligned (equal (car row) 10)))))) data))
(defun EL:PowerTextNumericChangeP (ref newdata / raw shown after before)
  (setq raw (EL:PowerTextRaw newdata) shown (if raw (EL:PowerTextDisplay raw (equal (EL:Get 'type ref) "MTEXT"))))
  (if (and shown (setq before (EL:PowerTextToken ref T))
      (setq after (EL:PowerTextToken (append (list (cons 'text raw)) shown) T)))
    (and (equal (EL:Get 'unit before) (EL:Get 'unit after))
      (equal (substr (EL:Get 'text ref) 1 (1- (EL:Get 'start before)))
        (substr raw 1 (1- (EL:Get 'start after))))
      (equal (substr (EL:Get 'text ref) (EL:Get 'end before)) (substr raw (EL:Get 'end after))))))
(defun EL:PowerTextWrittenP (ref newdata / entity after)
  ;; Also used after the complete batch: a later native callback may have
  ;; changed an earlier item even when that item's own write read back well.
  (setq entity (handent (EL:Get 'handle ref)) after (if entity (EL:PowerTextRead entity)))
  (and after (equal (EL:Get 'drawing-owner ref) (namedobjdict))
    (equal (EL:Get 'owner after) (EL:Get 'owner ref))
    (equal (EL:Get 'parent-data after) (EL:Get 'parent-data ref))
    (equal (EL:PowerTextRaw newdata) (EL:Get 'text after))
    (equal (EL:PowerTextNonContent newdata T) (EL:PowerTextNonContent (EL:Get 'data after) T))))
(defun EL:PowerTextWrite (ref newdata / entity current parent)
  (EL:Require *EL:TransactionOpen* "更新已有功率必须在完整事务中执行。")
  (setq entity (handent (EL:Get 'handle ref)) current (if entity (EL:PowerTextRead entity)))
  (EL:Require (and current (equal (EL:Get 'drawing-owner ref) (namedobjdict))
    (equal (EL:Get 'owner ref) (EL:Get 'owner current))
    (equal (EL:Get 'parent-data ref) (EL:Get 'parent-data current))
    (equal (EL:Get 'data ref) (EL:Get 'data current))) "已有功率对象或所属图块已变化，请重新复核。")
  (EL:Require (and newdata (equal (EL:PowerTextNonContent (EL:Get 'data ref) nil)
      (EL:PowerTextNonContent newdata nil)) (EL:PowerTextNumericChangeP ref newdata))
    "功率更新包含数字以外的变化，未写入。")
  (if (not (equal (EL:Get 'data ref) newdata))
    (progn
      (EL:Require (EL:PerfWrite 'entmod (list newdata)) "已有功率文字写入失败。")
      (if (EL:Get 'owner ref)
        (progn
          (setq parent (handent (EL:Get 'owner ref)))
          (EL:Require (EL:PerfWrite 'entupd (list parent)) "功率属性刷新失败。")))
      (EL:Require (EL:PowerTextWrittenP ref newdata)
        "已有功率文字回读不符，已停止本次更新。"))) T)
(princ)
