;; APPLOAD this file; keep the entire repository on an AutoCAD trusted path.
(setq *EL:BootstrapTick* (getvar "MILLISECS"))
(vl-load-com)
(defun EL:LoadModules (/ path el-file missing token *EL:MonitorLabel*)
  (if (not *EL:Root*)
    (progn
      (setq path (findfile "load.lsp"))
      (if (not path) (setq path (getfiled "请选择本插件 src/load.lsp 以确定根目录" "" "lsp" 0)))
      (if path (setq *EL:Root* (strcat (vl-filename-directory path) "/../")))))
  (if (and *EL:Root* (>= (getvar "LISPSYS") 1))
    (progn
      (foreach el-file '("common" "config" "geometry" "topology" "statistics" "device-library" "device-assets" "device-defaults" "device-ui" "device-recognition" "device-inputs" "device-migration" "generation" "main" "simple" "circuit-number" "fixed" "panel" "store-compact" "diagram-store" "store-split" "diagram-update" "diagram-commands" "insert-circuit" "cold-probe")
        (if (not (findfile (strcat *EL:Root* "src/" el-file ".lsp"))) (setq missing T)))
      (if missing (princ "\n插件文件不完整；检查 *EL:Root* 和 src 目录。")
        (progn
          (foreach el-file '("common" "config" "geometry" "topology" "statistics" "device-library" "device-assets" "device-defaults" "device-ui" "device-recognition" "device-inputs" "device-migration" "generation" "main" "simple" "circuit-number" "fixed" "panel" "store-compact" "diagram-store" "store-split" "diagram-update" "diagram-commands" "insert-circuit" "cold-probe")
            (if (equal el-file "common")
              (progn (load (strcat *EL:Root* "src/" el-file ".lsp"))
                (EL:MonitorLoadBegin *EL:BootstrapTick*))
              (progn (setq *EL:MonitorLabel* (strcat el-file ".lsp") token (EL:PerfBegin "LOAD_MODULE"))
                (load (strcat *EL:Root* "src/" el-file ".lsp")) (EL:PerfEnd token 'returned))))
          (EL:PerfCall "LOAD_LIBRARY" 'EL:DLDefaultStartup nil)
          (EL:MonitorLoadEnd 'load-finished)
          (princ "\n已加载：ELSETUP / ELPRESET / ELDEVPICK / ELDEVLIB / ELJBOX / ELGAPTEST / ELSTAT / ELPOWER / ELTEMPLATE / ELGEN / ELSTORELEGACY / CCKK。")
          (princ "\n启动命令：输入 ELSTAT 开始统计；ELDEVLIB 打开设备库。"))))
    (princ "\n需要 AutoCAD 2021+ Windows、LISPSYS=1/2（更改后重启）及完整插件目录。")))
(EL:LoadModules)
(princ)
