;; Date: 2026-10-14. Source checks and generation without in-place updates.
(defun EL:Require (condition message)
  ;; Date: 2026-10-10. Preserve validation reason before exit becomes a generic abort.
  (if (not condition) (progn (EL:LogEvent "VALIDATION_FAILED" (list (cons 'message message)))
    (princ (strcat "\n" message)) (exit))) T)
(defun EL:ActualRows (record)
  (vl-remove-if '(lambda (r) (equal (EL:Get 'mode r) 'reserve)) (EL:Get 'rows record)))
(defun EL:TextPoint (e / d)
  (setq d (entget e))
  (if (and (= (cond ((cdr (assoc 72 d))) (T 0)) 0) (= (cond ((cdr (assoc 73 d))) (T 0)) 0))
    (cdr (assoc 10 d)) (cdr (assoc 11 d))))
(defun EL:DynamicUpdate (e property value / obj before prop)
  (setq obj (vlax-ename->vla-object e) before (cdr (assoc 10 (entget e))) prop (EL:DynamicProperty obj property))
  (EL:Require prop "动态属性不存在。")
  (if (not (equal (vlax-variant-value (vla-get-Value prop)) value))
    (EL:Require (EL:SetDynamicValue obj property value) "动态属性写入或回读失败。"))
  (EL:Require (equal before (cdr (assoc 10 (entget e))) 1.0e-6) "动态状态切换导致基点漂移。"))
;; Date: 2026-10-14. A failed new generation marks only the current draft.
(defun EL:MarkStale (panel reason / store record)
  (if (and panel (setq store (EL:StoreForResult (list (cons 'panel panel)))) (setq record (EL:DiagramForPanel panel store)))
    (progn
      (setq record (EL:Put 'status 'stale (EL:Put 'stale-reason reason record)))
      (EL:Transaction 'EL:StoreWrite (list (EL:StorePutDiagram record store)))
      (princ "\n本次未生成新系统图；已保存的输入仍可重新核对。"))) nil)
(defun EL:NewRecord (panel store / id prefix serial row)
  ;; HANDSEED is not a portable GETVAR string. Allocate within this DWG store.
  (EL:Require (and (equal (type panel) 'STR) (/= panel "")
    (equal (type (EL:Get 'drawing-uuid store)) 'STR) (/= (EL:Get 'drawing-uuid store) ""))
    "无法建立系统图身份：图纸标识或来源箱体句柄为空。")
  (setq prefix (strcat (EL:Get 'drawing-uuid store) "/" panel "/")
    serial (1+ (cond ((EL:Get panel (EL:Get 'diagram-serials store))) (T 0))))
  (foreach row (EL:Get 'diagrams store)
    (setq serial (max serial (1+ (EL:DiagramSerial (EL:Get 'diagram-id row) panel store)))))
  (setq
    id (strcat prefix (itoa serial)))
  (while (EL:By 'diagram-id id (EL:Get 'diagrams store))
    (setq serial (1+ serial) id (strcat prefix (itoa serial))))
  (list (cons 'diagram-id id) (cons 'source-panel-handle panel) '(capacity-option . cap300) '(capacity-source . default)
    '(template-version . 1) '(status . unverified)))
(defun EL:RecognizeFixed (cfg panel / snapshot network result record keys perf
    *EL:RecognitionPass* *EL:RecognitionContacts*
    *EL:StableSnapshotMemo* *EL:StableSnapshotOwner* *EL:StableSnapshotEpoch*)
  (setq *EL:RecognitionPass* T cfg (EL:CurrentJunctionConfig cfg))
  (setq perf (EL:PerfBegin "RECOGNIZE_FIXED_RUN"))
  (EL:PerfCount "recognize-fixed-calls" 1)
  (EL:Require (and (handent panel) (not (EL:ManagedEntity (handent panel)))) "来源配电箱缺失或为受管输出。")
  (setq snapshot (EL:LogCall "SIMPLE_COLLECT" (list (cons 'panel panel)) 'EL:SimpleCollect (list cfg))
    snapshot (cond ((EL:Get 'circuit-starts cfg) (EL:StartSnapshot snapshot cfg panel))
      ((EL:Get 'concentrated-trunk cfg) (EL:TrunkSnapshot snapshot cfg panel)) (T snapshot))
    network (EL:LogCall "SIMPLE_NETWORK" (list (cons 'panel panel) (cons 'wires (length (EL:Get 'wires snapshot)))
      (cons 'blocks (length (EL:Get 'blocks snapshot)))) 'EL:SimpleNetwork (list snapshot cfg panel)))
  (setq result (EL:SelectFixedExits (EL:ClassifyStartLinks (EL:SplitNativeNumberBranches
    (EL:LogCall "SPLIT_NETWORK" (list (cons 'panel panel)) 'EL:SplitNetwork (list network cfg)) network cfg) cfg) nil))
  (if *EL:CollectMemo*
    (setq *EL:CollectMemo* (EL:Put 'input snapshot (EL:Put 'signature
      (EL:Get 'signature (EL:Get 'snapshot result)) *EL:CollectMemo*))))
  (EL:PerfSet "wire-count" (length (EL:Get 'wires snapshot)))
  (EL:PerfSet "block-count" (length (EL:Get 'blocks snapshot)))
  ;; Date: 2026-10-21. Distinguish whole selection candidates from this root walk.
  (EL:PerfSet "recognized-connected-wires" (length (EL:Get 'wire-ids network)))
  (EL:PerfSet "recognized-connected-devices" (length (EL:Get 'devices network)))
  (EL:LogEvent "RECOGNIZED_CONNECTED_SCOPE" (list (cons 'panel panel)
    (cons 'wires (length (EL:Get 'wire-ids network))) (cons 'devices (length (EL:Get 'devices network)))))
  (EL:PerfEnd perf 'returned) result)
(defun EL:FixedFreshSnapshotFull (cfg panel / snapshot network)
  ;; Date: 2026-10-11. Identical collect/network/CircuitSnapshot signature,
  ;; without tracing circuits or selecting exits just to compare the source.
  (EL:Require (and (handent panel) (not (EL:ManagedEntity (handent panel)))) "来源配电箱缺失或为受管输出。")
  (EL:PerfCount "freshness-scan-calls" 1)
  (setq snapshot (EL:LogCall "SIMPLE_COLLECT" nil 'EL:SimpleCollect (list cfg))
    snapshot (cond ((EL:Get 'circuit-starts cfg) (EL:StartSnapshot snapshot cfg panel))
      ((EL:Get 'concentrated-trunk cfg) (EL:TrunkSnapshot snapshot cfg panel)) (T snapshot))
    network (EL:LogCall "SIMPLE_NETWORK" nil 'EL:SimpleNetwork (list snapshot cfg panel)))
  (EL:CircuitSnapshot (EL:Get 'snapshot network) panel))
(defun EL:FixedFreshSnapshot (cfg panel)
  (setq cfg (EL:CurrentJunctionConfig cfg))
  (if *EL:FreshSourceCandidate* (EL:FixedFreshForResult cfg *EL:FreshSourceCandidate*)
    (EL:FixedFreshSnapshotFull cfg panel)))
(defun EL:FixedFreshForResult (cfg result / snapshot network proof epoch panel owner answer native-current
    *EL:DeviceContactCache* *EL:DeviceTemplateCache* *EL:DeviceTemplateEnabled*)
  (setq owner (namedobjdict) panel (EL:Get 'panel result) epoch *EL:FreshEpoch* *EL:DeviceTemplateEnabled* T
    proof (EL:Get 'network-proof (EL:Get 'snapshot result)))
  (EL:Require (and (handent panel) (not (EL:ManagedEntity (handent panel)))) "来源配电箱缺失或为受管输出。")
  (EL:PerfCount "freshness-scan-calls" 1)
  (setq native-current (EL:PerfCall "SOURCE_NATIVE_VERIFY" 'EL:CollectSourceCurrent (list cfg result)))
  (if native-current (setq snapshot native-current)
    (setq snapshot (EL:LogCall "SIMPLE_COLLECT" nil 'EL:SimpleCollect (list cfg))
      snapshot (cond ((EL:Get 'circuit-starts cfg) (EL:StartSnapshot snapshot cfg panel))
        ((EL:Get 'concentrated-trunk cfg) (EL:TrunkSnapshot snapshot cfg panel)) (T snapshot))))
  (setq answer (if (and (not *EL:NetworkReuseDisabled*) (equal (EL:Get 'version proof) 4) (equal panel (EL:Get 'panel proof))
      (equal (EL:StableData (vl-remove-if '(lambda (row) (equal (car row) 'template)) cfg)) (EL:Get 'config proof))
      (not (EL:Get 'issues snapshot))
      (or native-current (equal (EL:StableData snapshot)
        (EL:NetworkProofInput (cadr (EL:Get 'signature (EL:Get 'snapshot result))) proof)))
      (EL:PerfCall "NETWORK_VERIFY_GEOMETRY" 'EL:NetworkGeometryCurrent (list (EL:Get 'contacts proof) snapshot))
      (equal epoch *EL:FreshEpoch*))
    (progn (EL:PerfCount "network-proof-reuses" 1) (EL:Get 'snapshot result))
    (progn
      (EL:PerfCount "network-proof-rebuilds" 1)
      (setq network (EL:LogCall "SIMPLE_NETWORK" nil 'EL:SimpleNetwork (list snapshot cfg panel)))
      (EL:CircuitSnapshot (EL:Get 'snapshot network) panel))))
  (EL:Require (and (equal owner (namedobjdict)) (equal epoch *EL:FreshEpoch*))
    "SOURCE_CHANGED：复核期间发生写入、交互或切图，请重新统计。") answer)
(defun EL:PersistSourceSignature (result cfg / context signature)
  (setq context *EL:FreshProofContext* signature (EL:Get 'signature (EL:Get 'snapshot result)))
  (if (and context (equal (EL:Get 'owner context) (namedobjdict))
      (equal (EL:Get 'epoch context) *EL:FreshEpoch*)
      (equal (EL:Get 'panel context) (EL:Get 'panel result))
      (equal (EL:Get 'config context) cfg) (equal (EL:Get 'original context) signature))
    (EL:Get 'verified context) signature))
(defun EL:FreshResult (result cfg / fresh key good *EL:FreshSourceCandidate*)
  (setq *EL:FreshSourceCandidate* result)
  (if (equal (EL:Get 'engine result) 'fixed) (setq cfg (EL:CurrentJunctionConfig cfg)))
  (setq key (list (EL:Get 'drawing cfg) (getvar "DWGNAME") (getvar "DWGPREFIX")
    (EL:Get 'panel result) (EL:RecognitionRules cfg)
    (EL:Get 'signature (EL:Get 'snapshot result)) *EL:FreshEpoch*))
  (if (and *EL:FreshScopeEnabled* (equal (EL:Get 'engine result) 'fixed)
      *EL:FreshScope* (equal key (car *EL:FreshScope*)))
    (progn (EL:PerfCount "freshness-reuses" 1) (setq fresh (cadr *EL:FreshScope*)))
    (setq fresh (if (equal (EL:Get 'engine result) 'fixed)
      (EL:PerfCall "FRESH_SOURCE_SCAN" 'EL:FixedFreshSnapshot (list cfg (EL:Get 'panel result)))
      (EL:CollectEndpointSnapshot cfg))))
  (setq good (EL:LogCall "COMPARE_SOURCE" nil 'EL:SourceCurrent (list result cfg fresh)))
  (setq good (and good (EL:LogCall "COMPARE_SOURCE_NUMBER" nil 'EL:NumberInputsCurrent (list result))))
  (if (and good *EL:FreshScopeEnabled* (equal (EL:Get 'engine result) 'fixed))
    (setq *EL:FreshScope* (list key fresh))
    (setq *EL:FreshScope* nil))
  (setq *EL:FreshProofContext* (if good (list (cons 'owner (namedobjdict))
    (cons 'epoch *EL:FreshEpoch*) (cons 'panel (EL:Get 'panel result)) (cons 'config cfg)
    (cons 'original (EL:Get 'signature (EL:Get 'snapshot result)))
    (cons 'verified (EL:Get 'signature fresh))))) good)
(defun EL:PreparedResult (result record / matched rows c edited key)
  (setq result (EL:DLRestoreRecord result record))
  ;; Date: 2026-10-11. Restore the saved number without overwriting a new pick.
  (if (not (assoc 'panel-number result))
    (setq result (EL:Put 'panel-number (EL:PanelNumber record) result)))
  ;; Date: 2026-10-10. Restore explicit per-block ground choices.
  (if (and (not (assoc 'block-ground result)) (assoc 'block-ground record))
    (setq result (EL:Put 'block-ground (EL:Get 'block-ground record) result)))
  (setq matched (EL:MatchCircuits (EL:Get 'circuits result) (EL:ActualRows record) (EL:Get 'diagram-id record)))
  (foreach c (EL:Get 'circuits matched)
    (setq edited (EL:By 'circuit-uid (EL:Get 'circuit-uid c) (EL:Get 'circuits result)))
    (if edited
      (foreach key '(is-ground ground-source ground-rule ground-evidence)
        (setq c (EL:Put key (EL:Get key edited) c))))
    (setq rows (cons c rows)))
  (if (not (EL:Get 'capacity-source result))
    (setq result (EL:Put 'capacity-source
      (cond ((if (EL:Get 'draft-circuits record) (EL:Get 'draft-capacity-source record) (EL:Get 'capacity-source record)))
        (T 'default)) result)))
  (EL:SortCircuitNumbers (EL:ResolveCircuitNumbers
    (EL:Put 'identity-ambiguous (vl-some '(lambda (c) (EL:Get 'identity-error c)) rows) (EL:Put 'circuits (reverse rows) result)))))
(defun EL:DiagramOutputRefs (record / refs row label)
  (setq refs (list (list (EL:Get 'panel-output-handle record) "panel" "panel")))
  (foreach row (EL:Get 'rows record)
    (setq refs (cons (list (EL:Get 'block-handle row) "circuit" (EL:Get 'circuit-uid row)) refs))
    (if (EL:Get 'text-handle row)
      (setq refs (cons (list (EL:Get 'text-handle row) "text" (EL:Get 'circuit-uid row)) refs))))
  (foreach label (EL:Get 'cckk-labels record)
    (setq refs (cons (list (EL:Get 'handle label) "text" (EL:Get 'uid label)) refs))) refs)
;; Date: 2026-10-10. Deleted output is recoverable; foreign objects are not deleted.
(defun EL:DiagramViewBounds (record store / ref entity bounds lo hi good)
  (setq good T)
  (foreach ref (EL:DiagramOutputRefs record)
    (setq entity (EL:OwnedEntity (car ref) store record (cadr ref) (caddr ref))
      bounds (if entity (EL:EntityBounds entity)))
    (if bounds
      (setq lo (if lo (mapcar 'min lo (car bounds)) (car bounds))
        hi (if hi (mapcar 'max hi (cadr bounds)) (cadr bounds)))
      (setq good nil)))
  (if (and good lo hi) (list lo hi)))
(defun EL:ShowDiagramBody (record store / bounds)
  (if (and (= (getvar "TILEMODE") 1) (> (getvar "CVPORT") 1))
    (progn
      (EL:FreshBoundary)
      (vla-Regen (vla-get-ActiveDocument (vlax-get-acad-object)) 1)
      (EL:FreshBoundary)
      (if (setq bounds (EL:DiagramViewBounds record store))
        (progn
          (EL:LogEvent "DIAGRAM_VIEW_BOUNDS" (list (cons 'panel (EL:Get 'panel-output-handle record))
            (cons 'rows (length (EL:Get 'rows record))) (cons 'bounds bounds)))
          (EL:FreshBoundary)
          (EL:SimpleZoom (car bounds) (cadr bounds))
          (EL:FreshBoundary) T)))))
(defun EL:ShowDiagram (record store / shown checkpoint)
  (setq checkpoint *EL:PerfPending*)
  (setq shown (vl-catch-all-apply 'EL:PerfCall (list "DIAGRAM_VIEW" 'EL:ShowDiagramBody (list record store))))
  (if (vl-catch-all-error-p shown) (EL:PerfUnwind checkpoint))
  (if (equal shown T)
    (progn (EL:LogEvent "DIAGRAM_VIEW_SHOWN" (list (cons 'panel (EL:Get 'panel-output-handle record))))
      (princ "\n已定位到完整系统图。") T)
    (progn
      (EL:LogEvent "DIAGRAM_VIEW_FAILED" (list (cons 'panel (EL:Get 'panel-output-handle record))
        (cons 'position (EL:Get 'position (EL:Get 'plan record)))
        (cons 'reason (if (vl-catch-all-error-p shown) (vl-catch-all-error-message shown) "OUTPUT_BOUNDS_OR_MODEL_VIEW_UNAVAILABLE"))))
      (princ (strcat "\n系统图已保存，但自动定位未完成；输出箱体句柄："
        (EL:Get 'panel-output-handle record) "，插入点："
        (vl-prin1-to-string (EL:Get 'position (EL:Get 'plan record))) "。请查看诊断日志。")) nil)))
(defun EL:SyncDiagram (result cfg powers capacity generate interactive)
  ;; Date: 2026-10-21. Native placement and writes retain their epoch boundaries.
  (EL:WithTemplateScope 'EL:SyncDiagramScoped (list result cfg powers capacity generate interactive *EL:FreshScope*)))
(defun EL:CCKK2DeferredSource (result cfg record generate interactive)
  ;; Date: 2026-10-14. An accepted panel submission may defer the second scan
  ;; to CreateDiagram's check immediately after the native placement click.
  (and generate interactive *EL:CCKK2Request* *EL:GenerationPreflight*
    (equal (EL:Get 'engine result) 'fixed)
    (not (EL:Get 'identity-ambiguous result))
    (equal (list (namedobjdict) result cfg) *EL:GenerationPreflight*)))
(defun EL:GenerationSourceCurrent (result cfg deferred)
  ;; Date: 2026-10-21. Parent includes its existing source/number subchecks.
  (EL:PerfCall "GENERATION_SOURCE_VERIFY" 'EL:GenerationSourceCheck (list result cfg deferred)))
(defun EL:GenerationSourceCheck (result cfg deferred)
  (if deferred
    (and (equal (car *EL:GenerationPreflight*) (namedobjdict))
      (equal cfg (EL:CurrentJunctionConfig cfg))
      (EL:LogCall "COMPARE_SOURCE_NUMBER" nil 'EL:NumberInputsCurrent (list result)))
    (EL:FreshResult result cfg)))
(defun EL:SyncDiagramScoped (result cfg powers capacity generate interactive scope / store record template point transform plan context outcome deferred perf *EL:NativePreview* *EL:FreshScope* *EL:FreshScopeEnabled* *EL:GenerationWarningsActive* *EL:GenerationReviewFlags*)
  (if (assoc 'effective-powers result) (setq powers (EL:Get 'effective-powers result)))
  (setq *EL:FreshScope* scope *EL:FreshScopeEnabled* T
    *EL:GenerationWarningsActive* (EL:Get 'generation-warning-mode result)
    capacity (EL:CapacityDefault capacity))
  (if (not generate)
    (EL:SaveDraft result cfg powers capacity)
    (progn
      (setq perf (EL:PerfBegin "GENERATION_CONTEXT"))
      (setq *EL:LastGeneratedId* nil
        store (cond ((EL:StoreForResult result)) (T (EL:StoreInitial)))
        record (cond ((EL:RecordForResult result store)) (T (EL:NewRecord (EL:Get 'panel result) store)))
        template (cond ((EL:Get 'template cfg)) ((EL:Get 'template record)))
        deferred (EL:CCKK2DeferredSource result cfg record generate interactive)
        result (EL:PerfCall "GENERATION_PREPARE" 'EL:PreparedResult (list result record)))
      (if (EL:Get 'generation-warning-mode result) (setq result (EL:GenerationResult result)))
      (EL:PerfEnd perf 'returned)
      (cond
        ((and (not (EL:Get 'generation-warning-mode result)) (not (EL:CircuitNumbersReady result)))
          (princ (strcat "\n" (EL:NumberProblemText result)))
          (EL:MarkStale (EL:Get 'panel result) 'circuit-number-pending))
        ((and (not (EL:Get 'generation-warning-mode result)) (not (EL:Get 'can-generate result)))
          (EL:PrintStatistics result)
          (EL:MarkStale (EL:Get 'panel result) 'invalid-result))
        ((and (not (EL:Get 'generation-warning-mode result)) (or (EL:Get 'identity-ambiguous result)
            (vl-some '(lambda (c) (EL:Get 'identity-error c)) (EL:Get 'circuits result))))
          (princ "\n出线种子身份不唯一，请修复源图后重新统计。")
          (EL:MarkStale (EL:Get 'panel result) 'identity-conflict))
        ((not (EL:GenerationVerify 'EL:GenerationSourceCurrent (list result cfg deferred) result
            'SOURCE_CHANGED "平面状态已变化，按本次显示快照生成"))
          (EL:MarkStale (EL:Get 'panel result) 'source-changed))
        (T
          ;; Date: 2026-10-14. An existing output is never an update target.
          ;; Keep its entities, but allocate a fresh identity for this output.
          (if (EL:Get 'panel-output-handle record)
            (setq record (EL:NewRecord (EL:Get 'panel result) store)))
          (EL:Require (and (<= 1 (length (EL:Get 'circuits result)))
              (<= (length (EL:Get 'circuits result)) 8))
            "本图块最多容纳8条实际回路，请拆箱后统计。")
          (EL:Require (and (tblsearch "STYLE" "ICDA-STYLE1")
              (EL:OutputLayerReady "SYS_系统标注_E") (EL:OutputLayerReady "TEL_TEXT"))
            "请补齐 ICDA-STYLE1 样式，并打开、解冻和解锁输出图层。")
          (EL:Require (and (EL:FixedTemplate template) (EL:TemplateRuntimeValid template cfg))
            "模板未适配或已变化，请运行 ELTEMPLATE。")
          (EL:Require (EL:UniqueDiagram store record)
            "新系统图身份无效；具体对象见 DIAGRAM_ASSOCIATION_CONFLICT。")
          (EL:Require (and (= (getvar "TILEMODE") 1) (> (getvar "CVPORT") 1))
            "请进入模型空间生成系统图。")
          ;; CCKK2 uses native mouse placement inside the transaction.
          (setq point (if *EL:CCKK2Request* '(0.0 0.0 0.0)
            (EL:PerfInput 'getpoint (list "\n选择系统图箱体插入点："))))
          (EL:Require point "插入取消。")
          (if (not *EL:CCKK2Request*) (EL:PerfMark "placement-confirmed"))
          (setq transform (list (cons 'position (trans point 1 0))
            '(rotation . 0.0) '(scale . 1.0))
            *EL:NativePreview* interactive
            plan (EL:FixedPlan result template capacity (EL:Get 'position transform)
              (EL:Get 'rotation transform) (EL:Get 'scale transform)))
          (EL:Require plan "回路计划无效。")
          (EL:PerfSet "actual-circuits" (length (EL:Get 'circuits result)))
          (EL:PerfSet "reserve-circuits"
            (- (length (EL:Get 'rows plan)) (length (EL:Get 'circuits result))))
          (EL:Require (EL:GenerationVerify 'EL:GenerationSourceCurrent (list result cfg deferred) result
              'SOURCE_CHANGED "提交前源图变化，按本次显示快照生成")
            "SOURCE_CHANGED：提交前源图变化，未生成。")
          (EL:Require (EL:GenerationVerify 'EL:DLSubmissionCurrent (list result) result
              'DEVICE_LIBRARY_CHANGED "设备库已变化，按当前功率生成")
            "设备库已变化，当前输入保留；请重新核对后生成。")
          (setq perf (EL:PerfBegin "GENERATION_RECORD"))
          (setq record (EL:Put 'draft-circuits nil (EL:Put 'draft-capacity nil
            (EL:Put 'capacity-option capacity (EL:Put 'template template
              (EL:Put 'config cfg (EL:Put 'engine (EL:Get 'engine result)
                (EL:Put 'source-signature nil
                  (EL:Put 'power-signature (EL:Signature (EL:Get 'power-config result))
                    (EL:Put 'powers powers (EL:Put 'status 'current
                      (EL:Put 'updated-at (getvar "CDATE") record))))))))))))
          (setq record (EL:Put 'panel-circuits (EL:Get 'circuits result) record))
          (if (assoc 'block-ground result)
            (setq record (EL:Put 'block-ground (EL:Get 'block-ground result) record)))
          (setq record (EL:Put 'candidate-keys (EL:Get 'candidate-keys result)
            (EL:Put 'capacity-source (EL:Get 'capacity-source result)
              (EL:Put 'draft-capacity-source nil record))))
          (setq record (EL:Put 'panel-number (EL:PanelNumber result) record)
            record (EL:RecordNumberInputs record result nil)
            record (EL:DLPersist result record)
            store (EL:Put 'fixed-template template store))
          (setq record (EL:GenerationReviewRecord (EL:InputRecord record) result))
          (EL:PerfEnd perf 'returned)
          (if *EL:PlacementOnly*
            (setq outcome (EL:Transaction 'EL:CCKK2CreateDiagram
              (list result template capacity plan record store)))
            (setq context (EL:TransactionVerifiedStore
              (if *EL:CCKK2Request* 'EL:CCKK2CreateDiagram 'EL:CreateDiagram)
              (list result template capacity plan record store))
              outcome (EL:Get 'outcome context)))
          (if (and outcome (listp outcome)
              (EL:Get 'panel-output-handle outcome)
              (or *EL:PlacementOnly*
                (equal outcome (EL:DiagramForPanel (EL:Get 'panel result)
                  (EL:TransactionVerifiedRead context)))))
            (progn
              (setq *EL:LastGeneratedId* (EL:Get 'diagram-id outcome))
              (EL:RememberDiagramDiagnostic outcome store)
              (princ (strcat "\n已生成新系统图："
                (itoa (length (EL:Get 'circuits result))) " 条实际回路，"
                (itoa (- (length (EL:Get 'rows plan))
                  (length (EL:Get 'circuits result)))) " 条预留，无预留功率文字。"))
              ;; Date: 2026-10-15. Keep the user's placement view. Regenerating
              ;; and zooming the whole drawing adds work after all output exists.
              T)
            (progn
              (EL:LogEvent "GENERATION_NOT_COMMITTED"
                (list (cons 'panel (EL:Get 'panel result))))
              nil)))))))
