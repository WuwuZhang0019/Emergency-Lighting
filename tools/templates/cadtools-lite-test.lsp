;; Date: 2026-10-20. Independent trial entry; build emits strict GB2312.
;; This entry registers a command only. Business loading starts on ELTEST.
(vl-load-com)
(defun ELTEST:Normalize (root)
  (if (and (equal (type root) 'STR) (/= root ""))
    (strcat (vl-string-right-trim "/\\" root) "/")))
(defun ELTEST:ValidRoot (root)
  (and root (findfile (strcat root "@MARKER@"))
    (findfile (strcat root "src/load.lsp"))))
(defun ELTEST:Candidate (path / root)
  (if (and (equal (type path) 'STR) (/= path ""))
    (progn
      (if (and (findfile path) (not (vl-file-directory-p path)))
        (setq path (vl-filename-directory path)))
      (setq root (ELTEST:Normalize path))
      (cond ((ELTEST:ValidRoot root) root)
        ((and root (ELTEST:ValidRoot (strcat root "../"))) (strcat root "../"))))))
(defun ELTEST:RegistryDirectory ()
  (vl-registry-read
    (strcat "HKEY_CURRENT_USER\\" (vlax-product-key)
      "\\Profiles\\" (getvar "CPROFILE") "\\Dialogs\\Appload") "MainDialog"))
(defun ELTEST:FindRoot (/ path root filename)
  (setq path (vl-catch-all-apply 'ELTEST:RegistryDirectory nil))
  (if (not (vl-catch-all-error-p path)) (setq root (ELTEST:Candidate path)))
  (foreach filename '("@MARKER@" "ELTEST.lsp" "load.lsp")
    (if (not root) (setq root (ELTEST:Candidate (findfile filename)))))
  (if (not root) (setq root (ELTEST:Candidate *EL:Root*)))
  (if (not root) (setq root (ELTEST:Candidate *EL:CADToolsRoot*)))
  (if (not root) (setq root (ELTEST:Candidate (getenv "ELTEST_@VERSION@"))))
  (if (not root) (setq root (ELTEST:Candidate (getenv "EL_CADTOOLS_@VERSION@"))))
  root)
(setq *ELTEST:Root* (ELTEST:FindRoot))
(defun c:ELTESTROOT (/ path root)
  ;; Only an explicitly invoked relocation command may display a picker.
  (if (setq path (getfiled "手动指定测试包根目录的 ELTEST.lsp" "ELTEST.lsp" "lsp" 0))
    (if (setq root (ELTEST:Candidate path))
      (progn
        (setq *ELTEST:Root* root)
        (setenv "ELTEST_@VERSION@" root)
        (princ (strcat "\n测试目录已设置：" root "；输入 ELTEST 开始。")))
      (princ "\n所选目录不是 @VERSION@ 测试包，原目录保持不变。")))
  (princ))
(defun c:ELTEST (/ outcome *EL:CADToolsRoot*)
  (if (not (ELTEST:ValidRoot *ELTEST:Root*))
    ;; APPLOAD may not update its recent directory until its dialog closes.
    ;; Retry automatic discovery now; never turn failure into a file dialog.
    (setq *ELTEST:Root* (ELTEST:FindRoot)))
  (if (ELTEST:ValidRoot *ELTEST:Root*)
    (progn
      (setq *EL:CADToolsRoot* *ELTEST:Root*)
      (princ (strcat "\n正在加载测试包 @VERSION@：" *ELTEST:Root*))
      ;; Reload the pinned entry even after CADTools has replaced shared commands.
      (setq outcome (vl-catch-all-apply 'load (list (strcat *ELTEST:Root* "src/load.lsp"))))
      (cond
        ((vl-catch-all-error-p outcome)
          (princ (strcat "\n测试包加载失败：" (vl-catch-all-error-message outcome))))
        ((and *EL:MonitorLoadReady* (equal *EL:LiteVersion* "@VERSION@")
            (equal *EL:Root* *ELTEST:Root*) C:ELSTAT)
          (setenv "ELTEST_@VERSION@" *ELTEST:Root*)
          (princ "\nELTEST 使用 @VERSION@；正在打开应急照明面板。")
          (c:ELSTAT))
        (T (princ (strcat "\n测试包尚未就绪："
          (if *EL:StartupError* *EL:StartupError* "请重新解压完整测试包。"))))))
    (princ "\n无法自动定位 @VERSION@ 测试包。请完整解压并 APPLOAD 本包的 ELTEST.lsp；如需主动改目录，运行 ELTESTROOT。本次未运行统计。"))
  (princ))
(princ "\n@VERSION@ 测试入口已注册：输入 ELTEST 开始。")
(princ)
