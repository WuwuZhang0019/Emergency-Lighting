;; Date: 2026-10-23. Independent read-only cold-path experiment; never publishes results.
;; Date: 2026-10-22. APPLY/catch must target an already defined Lisp function.
;; Resolve the external .NET function inside that protected function body.
;; Date: 2026-10-22. Bounded checkpoints preserve context across catch/cleanup.
(defun EL:ColdCheckpoint (phase details / item)
  (foreach item details
    (setq *EL:ColdContext* (EL:Put (car item) (cdr item) *EL:ColdContext*)))
  (setq *EL:ColdContext* (EL:Put 'phase phase *EL:ColdContext*))
  (EL:LogEvent "COLD_CHECKPOINT" (list (cons 'phase phase) (cons 'details details))))
(defun EL:ColdFailure (message)
  (EL:LogEvent "COLD_FAILURE" (list (cons 'error message) (cons 'context *EL:ColdContext*)))
  (princ (strcat "\n原型失败阶段：" (EL:LogText (EL:Get 'phase *EL:ColdContext*))
    "\n原型诊断上下文：" (EL:LogText *EL:ColdContext*))))
(defun EL:ColdReplySummary (reply / payload textdata)
  (setq payload (EL:ColdNativePayload reply)
    textdata (if (and (listp payload) (equal (type (car payload)) 'STR)) (car payload)))
  (list (cons 'reply-type (type reply)) (cons 'payload-type (type payload))
    (cons 'native-status (cond
      ((and textdata (vl-string-search "\"status\":\"PROTOTYPE_COARSE_ONLY\"" textdata)) "PROTOTYPE_COARSE_ONLY")
      ((and textdata (vl-string-search "\"status\":\"ERROR\"" textdata)) "ERROR") (T "UNRECOGNIZED")))
    (cons 'json-length (if textdata (strlen textdata)))
    (cons 'json-prefix (if textdata (substr textdata 1 4096)))
    (cons 'json-truncated (and textdata (> (strlen textdata) 4096)))))
(defun EL:ColdNativePing ()
  (ELNETCOLD84 "EL_NET_COLD_PING_V1"))
(defun EL:ColdNativeInvoke (selection panel roots tolerance dmax boundary reportpath)
  (ELNETCOLD84 selection panel roots tolerance dmax boundary reportpath))
(defun EL:ColdNativeReady (/ reply ready)
  (EL:LogEvent "COLD_NATIVE_HANDSHAKE_BEGIN" (list (cons 'entry "ELNETCOLD84")))
  (setq reply (vl-catch-all-apply 'EL:ColdNativePing nil)
    ready (and (not (vl-catch-all-error-p reply))
      (or (and (equal (type reply) 'STR) (equal reply "EL_NET_COLD_PROBE_V1/0.1.84"))
        (and (listp reply) (= (length reply) 1) (equal (type (car reply)) 'STR)
          (equal (car reply) "EL_NET_COLD_PROBE_V1/0.1.84")))))
  (EL:LogEvent "COLD_NATIVE_HANDSHAKE" (list (cons 'ready ready)
    (cons 'response (if (not (vl-catch-all-error-p reply)) reply))
    (cons 'error (if (vl-catch-all-error-p reply) (vl-catch-all-error-message reply)))))
  ready)
(defun EL:ColdNativePayload (reply)
  ;; ResultBuffer list marshalling may enclose the explicit outer ListBegin.
  ;; Accept at most that one envelope; the payload/status check remains strict.
  (if (and (listp reply) (= (length reply) 1) (listp (car reply))) (car reply) reply))
(defun EL:ColdLoad (/ path)
  (if (not (EL:ColdNativeReady))
    (progn
      (setq path (strcat *EL:Root* "native/EmergencyLighting.ColdRecognition84.dll"))
      (EL:Require (findfile path) "缺少只读 .NET 原型 DLL，请保留完整 v0.1.84 交付目录。")
      (EL:LogEvent "COLD_NATIVE_LOAD_BEGIN" (list (cons 'dll path)))
      (command "_.NETLOAD" path)
      (EL:LogEvent "COLD_NATIVE_LOAD_RETURNED" (list (cons 'dll path)))))
  (EL:Require (EL:ColdNativeReady)
    "只读 .NET 原型握手失败，尚未开始采集；请检查 NETLOAD 错误及受信任路径，运行 ELDIAG 导出加载详情。"))
(defun EL:ColdRootHandles (cfg / text row)
  (setq text "")
  (foreach row (EL:Get 'circuit-starts cfg)
    (setq text (strcat text (if (= text "") "" ",") (EL:Get 'wire row)))) text)
(defun EL:ColdLegacy (cfg panel / result *EL:CollectMemo* *EL:NetworkMemo* *EL:RecognitionContacts*
    *EL:StableSnapshotMemo* *EL:StoreReadCache* *EL:NetworkReuseDisabled*
    *EL:TraceDiagnostics* *EL:TraceDiagnosticCount* *EL:TraceDiagnosticOmitted*)
  ;; Dynamic bindings isolate caches and opt-in evidence, even on failure.
  (setq *EL:NetworkReuseDisabled* T *EL:TraceDiagnostics* T
    *EL:TraceDiagnosticCount* 0 *EL:TraceDiagnosticOmitted* 0)
  (setq result (EL:RecognizeFixed cfg panel))
  (EL:LogEvent "COLD_TRACE_DIAGNOSTICS" (list (cons 'closed-edge-records *EL:TraceDiagnosticCount*)
    (cons 'closed-edge-omitted *EL:TraceDiagnosticOmitted*) '(record-limit . 20)))
  result)
;; Date: 2026-10-22. Procedure return and per-circuit business problems are separate.
(defun EL:ColdHead (items limit / out)
  (repeat limit (if items (setq out (cons (car items) out) items (cdr items))))
  (reverse out))
(defun EL:ColdLegacySummary (result / circuits circuit issues row rows count incomplete empty issuecount)
  (setq circuits (EL:Get 'circuits result) count 0 incomplete 0 empty 0 issuecount 0)
  (foreach circuit circuits
    (setq count (1+ count) issues (EL:Get 'issues circuit))
    (if (not (EL:Get 'complete circuit)) (setq incomplete (1+ incomplete)))
    (if (not (EL:Get 'devices circuit)) (setq empty (1+ empty)))
    (setq issuecount (+ issuecount (length issues)))
    (if (<= count 32)
      (progn
        (setq row (list (cons 'id (EL:Get 'id circuit))
          (cons 'seed (EL:Get 'wire (EL:Get 'seed circuit))) (cons 'seed-key (EL:Get 'seed-key circuit))
          (cons 'circuit-number (EL:Get 'circuit-number circuit))
          (cons 'complete (EL:Get 'complete circuit))
          (cons 'wire-count (length (EL:Get 'wires circuit)))
          (cons 'device-count (length (EL:Get 'devices circuit)))
          (cons 'issue-count (length issues)) (cons 'issues (EL:ColdHead issues 10))
          (cons 'issues-truncated (> (length issues) 10))))
        (EL:LogEvent "COLD_LEGACY_CIRCUIT" row)
        (setq rows (cons row rows)))))
  (list '(diagnostic-revision . "2026-10-22-legacy2")
    (cons 'result-present (if result T nil)) (cons 'business-complete (EL:Get 'complete result))
    (cons 'circuits count) (cons 'incomplete-circuits incomplete) (cons 'zero-device-circuits empty)
    (cons 'global-issue-count (length (EL:Get 'issues result)))
    (cons 'snapshot-issue-count (length (EL:Get 'issues (EL:Get 'snapshot result))))
    (cons 'circuit-issue-count issuecount) '(circuit-record-limit . 32)
    (cons 'circuits-omitted (max 0 (- count 32))) (cons 'circuit-details (reverse rows))))
(defun EL:ColdLegacyFeedback (summary / row issue shown)
  (princ (strcat "\n完整旧路径结果：" (itoa (EL:Get 'circuits summary)) " 条回路，"
    (itoa (EL:Get 'incomplete-circuits summary)) " 条未完成，"
    (itoa (EL:Get 'circuit-issue-count summary)) " 项回路问题，"
    (itoa (EL:Get 'zero-device-circuits summary)) " 条零设备回路。"))
  (setq shown 0)
  (foreach row (EL:Get 'circuit-details summary)
    (if (and (< shown 10) (or (not (EL:Get 'complete row))
        (> (EL:Get 'issue-count row) 0) (= (EL:Get 'device-count row) 0)))
      (progn
        (setq shown (1+ shown))
        (princ (strcat "\n回路 " (EL:LogText (EL:Get 'id row)) "：设备 "
          (itoa (EL:Get 'device-count row)) "，问题 " (itoa (EL:Get 'issue-count row))))
        (foreach issue (EL:ColdHead (EL:Get 'issues row) 3)
          (princ (strcat " / " (EL:LogText (EL:Get 'code issue)) "，对象 "
            (EL:LogText (EL:Get 'object issue)) "，关联 " (EL:LogText (EL:Get 'detail issue))))))))
  (princ "\n本命令为只读对照，不打开统计面板；面板测试请 APPLOAD 同包 ELFULL84.lsp 后运行 ELFULL84。"))
(defun EL:ColdBoundsAudit (samples / row actual checked missing different verdict)
  ;; This COM parity audit is outside managed timing and is separately reported.
  (setq checked 0 missing 0 different 0)
  (foreach row samples
    (setq actual (if (handent (car row)) (EL:EntityBounds (handent (car row)))))
    (setq checked (1+ checked))
    (setq verdict (cond ((not actual) (setq missing (1+ missing)) 'missing)
      ((not (equal actual (cdr row) 0.000001)) (setq different (1+ different)) 'different)
      (T 'matching)))
    ;; Native reports at most 16 samples; retain a hard diagnostic cap as well.
    (if (<= checked 16)
      (EL:LogEvent "COLD_BOUNDS_SAMPLE" (list (cons 'handle (car row))
        (cons 'expected (cdr row)) (cons 'actual actual) (cons 'verdict verdict)))))
  (list (cons 'checked checked) (cons 'missing missing) (cons 'different different)))
(defun EL:ColdReportPath (extension)
  (strcat *EL:Root* "output/ELCOLD84-" (rtos (getvar "CDATE") 2 8)
    "-" (itoa (EL:Tick)) extension))
(defun EL:ColdRun (/ mode pick panel saved cfg started loaded selected returned audited finished
    owner epoch ss payload audit nativepath reportpath report legacy legacy-start legacy-end result rows row legacy-summary panelroute)
  (setq *EL:ColdCompleted* nil *EL:ColdContext* nil)
  ;; Date: 2026-10-22. An early failure must not export a previous run's reports.
  (setq *EL:ColdReports* (EL:Put (namedobjdict) nil *EL:ColdReports*))
  (setq panelroute '((entry . "ELCOLD84") (policy . readonly-comparison)
    (panel-requested . nil) (panel-file . "ELFULL84.lsp") (panel-command . "ELFULL84")))
  (EL:ColdCheckpoint "MODE" (list '(diagnostic-revision . "2026-10-22-logs1")
    '(legacy-diagnostic-revision . "2026-10-22-legacy2") (cons 'panel-route panelroute)))
  (EL:LogEvent "COLD_PANEL_ROUTE" panelroute)
  (princ "\nELCOLD84：只读冷路径性能原型；当前 .NET 仅验证批量读取、索引及保守候选发现，不替代完整识别。")
  (princ "\n此入口不打开统计面板；面板测试请 APPLOAD 同包 ELFULL84.lsp 后运行 ELFULL84。")
  (initget "Both Prototype")
  (setq mode (getkword "\n模式 [完整旧路径对照(Both)/仅原型(Prototype)] <Both>："))
  (if (not mode) (setq mode "Both"))
  (EL:ColdCheckpoint "PICK_PANEL" (list (cons 'mode mode)))
  (if (setq pick (EL:PickModel 'panel "\n拾取本次测试的新配电箱："))
    (progn
      (setq panel (cdr (assoc 5 (entget (car pick)))))
      (EL:Require (not (EL:ManagedEntity (car pick))) "请选择平面配电箱。")
      (EL:ColdCheckpoint "LOAD_CONFIG" (list (cons 'panel panel) (cons 'drawing (EL:DrawingID))))
      (setq saved (EL:LoadConfig))
      (EL:Require saved "图纸配置读取失败，请先检查现有识别预设。")
      (setq cfg (EL:Put 'roles (EL:Get 'roles saved) (EL:Put 'auto-panel panel
        (EL:Put 'params (EL:FixedRecognitionParams saved)
          (EL:PresetConfig (EL:DefaultConfig (EL:DrawingID)))))))
      (EL:ColdCheckpoint "PRESET_READY" nil)
      (if (and (setq cfg (EL:PresetReady (car pick) cfg))
          (progn (EL:ColdCheckpoint "PICK_STARTS" nil) (setq cfg (EL:PickCircuitStarts cfg))))
        (progn
          ;; Start before clearing the pick overlay, selecting, NETLOAD and the first JIT.
          (setq started (EL:Tick))
          (EL:ClearGapPreview) (EL:ClearPickHighlights)
          (EL:ColdCheckpoint "NATIVE_LOAD" (list (cons 'roots (EL:ColdRootHandles cfg))
            (cons 'root-count (length (EL:Get 'circuit-starts cfg)))
            (cons 'circuit-starts (EL:Get 'circuit-starts cfg))
            (cons 'device-tolerance (EL:DeviceContactTolerance cfg))
            (cons 'dmax (EL:Get 'Dmax (EL:Get 'params cfg)))
            (cons 'boundary-tolerance (EL:Get 'eps_boundary (EL:Get 'params cfg)))))
          (EL:PerfCall "COLD_NATIVE_LOAD" 'EL:ColdLoad nil)
          (setq loaded (EL:Tick) owner (namedobjdict) epoch *EL:FreshEpoch*
            nativepath (EL:ColdReportPath ".json") reportpath (EL:ColdReportPath ".eld"))
          (EL:ColdCheckpoint "SELECTION" (list (cons 'native-report nativepath) (cons 'comparison-report reportpath)
            (cons 'wire-layers (EL:Get 'wire-layers cfg))
            (cons 'panel-layers (EL:Get 'panel-layers cfg)) (cons 'device-layers (EL:Get 'device-layers cfg))))
          (setq ss (EL:PresetSelection cfg "INSERT,LINE,LWPOLYLINE" '(wire-layers panel-layers device-layers))
            selected (EL:Tick))
          ;; Register paths before native dispatch so ELDIAG includes failed native reports.
          (setq *EL:ColdReports* (EL:Put owner (list nativepath reportpath) *EL:ColdReports*))
          (EL:ColdCheckpoint "NATIVE_PROBE" (list (cons 'selection-type (type ss))
            (cons 'selection-count (if ss (sslength ss)))))
          (EL:Require ss "预设范围没有可测试对象。")
          (EL:LogEvent "COLD_NATIVE_PROBE_BEGIN" (list (cons 'entry "ELNETCOLD84")
            (cons 'panel panel) (cons 'roots (EL:ColdRootHandles cfg)) (cons 'report nativepath)))
          (setq payload (EL:MeasuredCatch 'EL:PerfCall (list "COLD_NATIVE_PROBE" 'EL:ColdNativeInvoke
            (list ss (handent panel) (EL:ColdRootHandles cfg)
              (EL:DeviceContactTolerance cfg) (EL:Get 'Dmax (EL:Get 'params cfg))
              (EL:Get 'eps_boundary (EL:Get 'params cfg)) nativepath))))
          (if (vl-catch-all-error-p payload)
            (progn
              (EL:LogEvent "COLD_NATIVE_PROBE_FAILED"
                (list (cons 'error (vl-catch-all-error-message payload)) (cons 'report nativepath)))
              (EL:Require nil (strcat "只读 .NET 原型调用失败：" (vl-catch-all-error-message payload)))))
          (EL:ColdCheckpoint "PAYLOAD_VALIDATE" (list (cons 'native-return (EL:ColdReplySummary payload))))
          (EL:LogEvent "COLD_NATIVE_RETURN" (EL:Get 'native-return *EL:ColdContext*))
          (setq payload (EL:ColdNativePayload payload) returned (EL:Tick))
          (if (not (and (listp payload) (equal (type (car payload)) 'STR)
              (vl-string-search "\"status\":\"PROTOTYPE_COARSE_ONLY\"" (car payload))))
            (EL:LogEvent "COLD_NATIVE_PROBE_FAILED" (EL:Get 'native-return *EL:ColdContext*)))
          (EL:Require (and (listp payload) (equal (type (car payload)) 'STR)
              (vl-string-search "\"status\":\"PROTOTYPE_COARSE_ONLY\"" (car payload)))
            "只读 .NET 原型失败，未产生识别结果；请导出 ELDIAG 检查原型报告。")
          (EL:ColdCheckpoint "BOUNDS_AUDIT" nil)
          (setq audit (EL:ColdBoundsAudit (cadr payload)) audited (EL:Tick))
          (EL:LogEvent "COLD_BOUNDS_AUDIT" audit)
          (EL:ColdCheckpoint "SOURCE_GUARD" (list (cons 'bounds-audit audit)
            (cons 'owner-same (equal owner (namedobjdict))) (cons 'epoch-before epoch)
            (cons 'epoch-after *EL:FreshEpoch*)))
          (EL:Require (and (equal owner (namedobjdict)) (equal epoch *EL:FreshEpoch*))
            "SOURCE_CHANGED：测试期间源图或当前图纸已变化，本次对照无效。")
          (if (equal mode "Both")
            (progn
              (princ "\n.NET 候选阶段完成；继续执行完整旧路径只读对照，另计耗时。")
              (EL:ColdCheckpoint "LEGACY_RECOGNITION" nil)
              (setq legacy-start (EL:Tick) result (EL:ColdLegacy cfg panel) legacy-end (EL:Tick))
              (EL:LogEvent "COLD_LEGACY_RETURN" (list (cons 'elapsed-ms (EL:PerfDelta legacy-start legacy-end))
                (cons 'result-type (type result)) (cons 'circuits (length (EL:Get 'circuits result)))
                (cons 'issues (EL:Get 'issues result))))
              (EL:ColdCheckpoint "LEGACY_SUMMARY" (list '(legacy-returned . T)))
              (setq legacy-summary (EL:ColdLegacySummary result))
              (EL:LogEvent "COLD_LEGACY_SUMMARY" legacy-summary)
              (setq legacy (list '(status . legacy-full-readonly)
                (cons 'circuits (length (EL:Get 'circuits result)))
                (cons 'summary legacy-summary) (cons 'result (EL:DiagnosticResult result))))))
          (EL:ColdCheckpoint "FINAL_SOURCE_GUARD" (list (cons 'owner-same (equal owner (namedobjdict)))
            (cons 'epoch-after *EL:FreshEpoch*)))
          (setq finished (EL:Tick))
          (EL:Require (and (equal owner (namedobjdict)) (equal epoch *EL:FreshEpoch*))
            "SOURCE_CHANGED：完整对照期间源图或当前图纸已变化，本次对照无效。")
          (EL:ColdCheckpoint "REPORT_WRITE" nil)
          (setq report (list '(version . 1) '(date . "2026-10-23") '(package . "v0.1.84")
            '(diagnostic-revision . "2026-10-22-logs1")
            '(legacy-diagnostic-revision . "2026-10-22-legacy2")
            (cons 'legacy-executed (equal mode "Both")) (cons 'panel-route panelroute)
            (cons 'bounds-audit-passed (and (= (EL:Get 'missing audit) 0) (= (EL:Get 'different audit) 0)))
            '(status . prototype-coarse-only) '(complete-native-recognition . nil)
            '(target-full-recognition-ms . 3000) '(target-achieved . unverified)
            '(readonly-drawing . T) '(previous-result-cache . nil)
            (cons 'drawing (EL:DrawingID)) (cons 'panel panel) (cons 'mode mode)
            (cons 'config cfg) (cons 'native-report nativepath)
            (cons 'load-and-clear-ms (EL:PerfDelta started loaded))
            (cons 'selection-and-path-ms (EL:PerfDelta loaded selected))
            (cons 'managed-bridge-ms (EL:PerfDelta selected returned))
            (cons 'bounds-audit-ms (EL:PerfDelta returned audited))
            (cons 'prototype-pick-to-return-ms (EL:PerfDelta started audited))
            (cons 'legacy-full-ms (if legacy-start (EL:PerfDelta legacy-start legacy-end)))
            (cons 'end-to-end-ms (EL:PerfDelta started finished)) (cons 'bounds-audit audit)
            (cons 'legacy legacy)))
          (EL:Require (EL:WriteData reportpath report) "原型对照报告写入失败。")
          (setq *EL:ColdReports* (EL:Put owner (list nativepath reportpath) *EL:ColdReports*))
          (setq *EL:ColdCompleted* T)
          (EL:ColdCheckpoint "FINISHED" (list (cons 'legacy-executed (equal mode "Both"))
            '(complete-native-recognition . nil) (cons 'bounds-audit-passed (EL:Get 'bounds-audit-passed report))))
          (EL:LogEvent "COLD_PROBE80" report)
          (princ (strcat "\n.NET 候选原型从拾取结束到返回："
            (itoa (EL:PerfDelta started audited)) " ms（含本次 NETLOAD、选择和边界抽查）。"))
          (if legacy-start (princ (strcat "\n完整旧路径只读识别："
            (itoa (EL:PerfDelta legacy-start legacy-end)) " ms。")))
          (princ (strcat "\n边界抽查：" (itoa (EL:Get 'checked audit)) " 项，缺失 "
            (itoa (EL:Get 'missing audit)) " 项，差异 " (itoa (EL:Get 'different audit)) " 项。"))
          (if (equal mode "Both") (EL:ColdLegacyFeedback legacy-summary)
            (princ "\n本次选择 Prototype，仅候选阶段完成；未执行完整旧路径识别，不会打开统计面板。"))
          (princ "\n当前原型尚未执行 .NET 精细识别与编号；完整首次识别 3 秒目标尚未验收。")
          (princ (strcat "\n原型报告：" nativepath "\n对照报告：" reportpath "\n运行 ELDIAG 可一并导出。")))))))
(defun c:ELCOLD84 (/ *error* outcome *EL:ColdCompleted* *EL:ColdContext*)
  (defun *error* (message)
    (vl-catch-all-apply 'EL:ClearGapPreview nil)
    (vl-catch-all-apply 'EL:ClearPickHighlights nil)
    (EL:ColdFailure message)
    (EL:LogFailure message) (EL:LogFinish 'cold-probe-failed)
    (if message (princ (strcat "\n只读原型已停止：" message))) (princ))
  (if (EL:EnsureRoot)
    (progn
      (EL:LogStart)
      ;; Date: 2026-10-22. The generic log name contains '/', invalid in a
      ;; Windows timeline filename. Name this command's own run explicitly.
      (if *EL:PerfLogOwner* (setq *EL:PerfCommand* "ELCOLD84"))
      (setq outcome (EL:MeasuredCatch 'EL:ColdRun nil))
      (EL:ClearGapPreview) (EL:ClearPickHighlights)
      (if (vl-catch-all-error-p outcome)
        (progn (EL:ColdFailure (vl-catch-all-error-message outcome))
          (EL:LogFailure (vl-catch-all-error-message outcome))
          (princ (strcat "\n只读原型未完成：" (vl-catch-all-error-message outcome)))))
      ;; Date: 2026-10-22. Native EXIT may return without a catch error.
      ;; Only a written and validated comparison report completes the probe.
      (if (and (not (vl-catch-all-error-p outcome)) (not *EL:ColdCompleted*))
        (EL:ColdFailure "本轮未写出完成报告；请检查最后阶段及取消操作。"))
      (EL:LogFinish (if (or (vl-catch-all-error-p outcome) (not *EL:ColdCompleted*))
        'cold-probe-failed 'cold-probe-finished))))
  (princ))
