;; Date: 2026-10-13. Update explicitly selected existing power labels only.
(defun EL:PowerOnlyResult (result record / key)
  (foreach key '(power-only-target power-only-scope power-only-bindings)
    (if (and (not (assoc key result)) (assoc key record))
      (setq result (EL:Put key (EL:Get key record) result)))) result)
(defun EL:PowerOnlyPersist (record result / key)
  (foreach key '(power-only-target power-only-scope power-only-bindings)
    (if (assoc key result) (setq record (EL:Put key (EL:Get key result) record)))) record)
(defun EL:PowerOnlyReady (result / seen number good row)
  (setq good (and (EL:Get 'can-generate result) (EL:Get 'circuits result)
    (EL:CircuitNumbersReady result)))
  (foreach row (EL:Get 'circuits result)
    (setq number (EL:Get 'circuit-number row))
    (if (and (EL:NumberTextValid number) (/= (EL:NumberKey number) "")
        (equal (EL:Get 'number-source row) 'plane)
        (equal (EL:Get 'number-status row) 'ready)
        (numberp (EL:Get 'watts row)) (>= (EL:Get 'watts row) 0)
        (<= (EL:Get 'watts row) 2147483647) (= (EL:Get 'watts row) (fix (EL:Get 'watts row))))
      (if (member (EL:NumberKey number) seen) (setq good nil)
        (setq seen (cons (EL:NumberKey number) seen)))
      (setq good nil))) (if good T nil))
(defun EL:PowerOnlyTargetValid (handle)
  (and (equal (type handle) 'STR) (handent handle) (EL:PowerTextLocalInsertP (handent handle))))
(defun EL:PowerOnlyChoose (result / pick target)
  (princ "\n仅更新功率：选择已有系统图箱体；回路图形、编号和其他文字保持原样。")
  (if (setq pick (EL:PickModel 'panel "\n拾取已有系统图箱体（Enter 返回）："))
    (progn
      (setq target (cdr (assoc 5 (entget (car pick)))))
      (EL:Require (and (/= target (EL:Get 'panel result)) (EL:PowerOnlyTargetValid target))
        "请选择本图模型空间的系统图箱体，不能选择平面来源箱体或外部参照。")
      (EL:Put 'power-only-target target
        (EL:Put 'power-only-scope nil (EL:Put 'power-only-bindings nil result))))))
(defun EL:PowerOnlySameRow (number power / angle delta tolerance)
  (setq angle (EL:Get 'angle number) delta (EL:V- (EL:Get 'point power) (EL:Get 'point number))
    tolerance (* 0.75 (max (EL:Get 'height number) (EL:Get 'height power))))
  (and (equal (sin (- angle (EL:Get 'angle power))) 0.0 0.00001)
    (<= (abs (+ (* (- (sin angle)) (car delta)) (* (cos angle) (cadr delta)))) tolerance)
    (<= (abs (caddr delta)) tolerance)))
(defun EL:PowerOnlyNumberRefs (result refs / rows circuit number matches)
  (foreach circuit (EL:Get 'circuits result)
    (setq number (EL:NumberKey (EL:Get 'circuit-number circuit))
      matches (vl-remove-if-not '(lambda (ref) (equal number (EL:NumberKey (EL:Get 'visible ref)))) refs))
    (EL:Require (= (length matches) 1)
      (strcat "系统图回路 " number (if matches " 编号重复" " 未找到编号")
        "；请用“关联原图功率”重新选定完整系统图范围。未写入功率。"))
    (setq rows (cons (list (cons 'number number) (cons 'number-ref (car matches))
      (cons 'watts (EL:Get 'watts circuit))) rows))) (reverse rows))
(defun EL:PowerOnlyManual (number refs used / pick ref done)
  (EL:HighlightPick (handent (EL:Get 'handle (EL:Get 'number-ref number))))
  (princ (strcat "\n回路 " (EL:Get 'number number) " 的功率位置不能唯一确定，已高亮编号。"))
  (while (not done)
    (if (setq pick (EL:PerfInput 'nentsel (list (strcat "\n点选 " (EL:Get 'number number)
        " 的现有功率文字（Enter 取消，本次不写入）："))))
      (progn
        (setq ref (EL:PowerTextRead (car pick)))
        (if (and ref (EL:By 'handle (EL:Get 'handle ref) refs)
            (not (member (EL:Get 'handle ref) used))
            (EL:PowerTextReplacement ref (EL:Get 'watts number) T))
          (setq done T)
          (progn (setq ref nil) (princ "\n请选择所选系统图范围内、未被其他回路占用的单个功率值。"))))
      (setq done T ref nil)))
  (EL:ClearPickHighlights) ref)
(defun EL:PowerOnlyMatch (result refs bindings interactive / numbers powers number candidates prior ref mode used rows after cancelled numberhandles)
  (setq numbers (EL:PowerOnlyNumberRefs result refs)
    numberhandles (mapcar '(lambda (n) (EL:Get 'handle (EL:Get 'number-ref n))) numbers)
    powers (vl-remove-if-not '(lambda (r) (and (not (member (EL:Get 'handle r) numberhandles))
      (EL:PowerTextReplacement r 0 nil))) refs))
  (foreach number numbers
    (if (not cancelled)
      (progn
        (setq prior (EL:By 'number (EL:Get 'number number) bindings) ref nil mode 'auto)
        (if prior
          (progn
            (setq ref (EL:By 'handle (EL:Get 'power-handle prior) refs) mode (EL:Get 'mode prior))
            (EL:Require (and ref
              (equal (EL:Get 'number-handle prior) (EL:Get 'handle (EL:Get 'number-ref number)))
              (equal (EL:Get 'owner prior) (EL:Get 'owner ref)))
              (strcat "回路 " (EL:Get 'number number) " 的原关联已失效；请点“关联原图功率”重新关联。"))))
        (if (not (equal mode 'manual))
          (progn
            ;; An automatic candidate must align with exactly ONE identified number.
            (setq candidates (vl-remove-if-not '(lambda (p) (and
              (EL:PowerOnlySameRow (EL:Get 'number-ref number) p)
              (= 1 (length (vl-remove-if-not '(lambda (n)
                (EL:PowerOnlySameRow (EL:Get 'number-ref n) p)) numbers))))) powers))
            (if prior
              (EL:Require (and (= (length candidates) 1)
                (equal (EL:Get 'handle ref) (EL:Get 'handle (car candidates))))
                (strcat "回路 " (EL:Get 'number number) " 的功率排版或候选已变化；请重新关联。"))
              (setq ref (if (= (length candidates) 1) (car candidates))))))
        (if (and (not ref) interactive)
          (setq ref (EL:PowerOnlyManual number (vl-remove-if '(lambda (r)
            (member (EL:Get 'handle r) numberhandles)) refs) used) mode 'manual))
        (if (not ref) (setq cancelled T)
          (progn
            (EL:Require (not (member (EL:Get 'handle ref) used)) "多个回路对应同一功率文字，未写入。")
            (setq after (EL:PowerTextReplacement ref (EL:Get 'watts number) (equal mode 'manual)))
            (EL:Require after (strcat "回路 " (EL:Get 'number number) " 的功率格式不能安全更新。"))
            (setq used (cons (EL:Get 'handle ref) used)
              rows (cons (append number (list (cons 'number-handle (EL:Get 'handle (EL:Get 'number-ref number)))
                (cons 'power-handle (EL:Get 'handle ref)) (cons 'owner (EL:Get 'owner ref))
                (cons 'mode mode) (cons 'power-ref ref) (cons 'after after))) rows)))))))
  (if (not cancelled) (reverse rows)))
(defun EL:PowerOnlyBindings (plan / row bindings)
  (foreach row plan (setq bindings (cons (list (cons 'number (EL:Get 'number row))
    (cons 'number-handle (EL:Get 'number-handle row)) (cons 'power-handle (EL:Get 'power-handle row))
    (cons 'owner (EL:Get 'owner row)) (cons 'mode (EL:Get 'mode row))) bindings))) (reverse bindings))
(defun EL:PowerOnlyRefs (handles / handle ref refs)
  (foreach handle handles
    (setq ref (EL:PowerTextRead (handent handle)))
    (EL:Require ref (strcat "原系统图文字 " handle " 已删除、锁定或不再可编辑；请重新关联。"))
    (setq refs (cons ref refs))) (reverse refs))
(defun EL:PowerOnlyRefCurrent (ref / current)
  (setq current (EL:PowerTextRead (handent (EL:Get 'handle ref))))
  (and current (equal (EL:Get 'data current) (EL:Get 'data ref))
    (equal (EL:Get 'parent-data current) (EL:Get 'parent-data ref))
    (equal (EL:Get 'drawing-owner current) (EL:Get 'drawing-owner ref))
    (equal (EL:Get 'owner current) (EL:Get 'owner ref))))
(defun EL:PowerOnlyPlanCurrent (plan / row ref good)
  (setq good T)
  (foreach row plan
    (foreach ref (list (EL:Get 'number-ref row) (EL:Get 'power-ref row))
      (if (not (EL:PowerOnlyRefCurrent ref)) (setq good nil)))) good)
(defun EL:PowerOnlyWritten (plan / row good)
  (setq good T)
  (foreach row plan
    (if (not (and (EL:PowerOnlyRefCurrent (EL:Get 'number-ref row))
        (EL:PowerTextWrittenP (EL:Get 'power-ref row) (EL:Get 'after row)))) (setq good nil))) good)
(defun EL:PowerOnlyApply (result cfg powers capacity record store plan / row key)
  (EL:Require (and (EL:PowerOnlyTargetValid (EL:Get 'power-only-target result))
    (EL:FreshResult result cfg) (EL:DLSubmissionCurrent result) (EL:PowerOnlyPlanCurrent plan))
    "平面编号、功率来源或目标文字在提交前变化，未更新。")
  (foreach row plan (EL:PowerTextWrite (EL:Get 'power-ref row) (EL:Get 'after row)))
  ;; Keep full-generation output members intact when the selected diagram was managed.
  (setq record (EL:PowerOnlyPersist record result)
    record (EL:Put 'source-panel-handle (EL:Get 'panel result) record)
    record (EL:Put 'power-only-bindings (EL:PowerOnlyBindings plan) record)
    record (EL:Put 'draft-circuits (EL:Get 'circuits result) (EL:Put 'draft-capacity capacity
      (EL:Put 'powers powers (EL:Put 'config cfg (EL:Put 'engine (EL:Get 'engine result) record))))))
  (setq record (EL:Put 'draft-source-signature (EL:PersistSourceSignature result cfg)
    (EL:Put 'panel-number (EL:PanelNumber result) (EL:Put 'status 'power-current
      (EL:Put 'updated-at (getvar "CDATE") record)))))
  (setq record (EL:Put 'draft-capacity-source (EL:Get 'capacity-source result) record))
  (setq record (EL:DLPersist result (EL:RecordNumberInputs record result T)))
  (foreach key '(block-ground excluded-devices candidate-keys excluded-seeds capacity-source)
    (if (assoc key result) (setq record (EL:Put key (EL:Get key result) record))))
  (EL:Require (EL:StoreWrite (EL:StorePutDiagram record store)) "功率关联保存失败，已停止本次更新。")
  ;; Check the entire batch after all graphic AND XRecord callbacks, while rollback is possible.
  (EL:Require (and (EL:FreshResult result cfg) (EL:DLSubmissionCurrent result)
    (EL:PowerOnlyTargetValid (EL:Get 'power-only-target result)) (EL:PowerOnlyWritten plan))
    "功率写入后复核不一致，已停止并撤销本次修改。") record)
(defun EL:UpdateExistingPower (result cfg powers capacity / store record refs selection plan context outcome row)
  (if (assoc 'effective-powers result) (setq powers (EL:Get 'effective-powers result)))
  (setq store (cond ((EL:StoreForResult result)) (T (EL:StoreInitial)))
    record (cond ((EL:RecordForResult result store)) (T (EL:NewRecord (EL:Get 'panel result) store)))
    result (EL:PowerOnlyResult result record))
  (EL:Require (EL:PowerOnlyReady result) "仅更新功率需要每条实际回路有明确的平面编号和有效功率；自动补出的 ZE 序号不能当作对应依据，请完善平面编号后重新统计。")
  (EL:Require (EL:PowerOnlyTargetValid (EL:Get 'power-only-target result)) "原系统图箱体失效，请点“关联原图功率”重新选择。")
  (if (EL:Get 'power-only-scope result)
    (setq refs (EL:PowerOnlyRefs (EL:Get 'power-only-scope result)))
    (progn
      (princ "\n选择这一张系统图的全部回路编号和功率文字（可框选，含属性时选所属块）；Enter 完成。")
      (setq selection (EL:PerfInput 'ssget (list '((0 . "TEXT,MTEXT,INSERT,ATTRIB") (410 . "Model")))))
      (if selection (setq refs (EL:PowerTextCollect selection)
        result (EL:Put 'power-only-scope (mapcar '(lambda (r) (EL:Get 'handle r)) refs) result)))))
  (if (and refs (setq plan (EL:PowerOnlyMatch result refs (EL:Get 'power-only-bindings result) T)))
    (progn
      (foreach row plan (princ (strcat "\n复核 " (EL:Get 'number row) "："
        (EL:Get 'text (EL:Get 'power-ref row)) " -> " (EL:PowerTextRaw (EL:Get 'after row)))))
      (EL:LogEvent "EXISTING_POWER_PLAN" (EL:PowerOnlyBindings plan))
      (setq context (EL:TransactionVerifiedStore 'EL:PowerOnlyApply (list result cfg powers capacity record store plan))
        outcome (EL:Get 'outcome context))
      (if (and outcome (equal outcome (EL:DiagramForPanel (EL:Get 'panel result) (EL:TransactionVerifiedRead context))))
        (progn (princ (strcat "\n已更新原系统图 " (itoa (length plan)) " 条回路功率；其余图形和文字未修改。")) outcome)))))
(defun EL:PowerOnlyTry (result cfg powers capacity / outcome)
  (setq outcome (vl-catch-all-apply 'EL:UpdateExistingPower (list result cfg powers capacity)))
  (if (vl-catch-all-error-p outcome)
    (progn (EL:ClearPickHighlights)
      (EL:LogEvent "EXISTING_POWER_FAILED" (vl-catch-all-error-message outcome))
      (princ (strcat "\n功率更新未完成，当前输入保留：" (vl-catch-all-error-message outcome))) nil)
    outcome))
